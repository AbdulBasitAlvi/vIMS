PROJECT-CLEARWATER-MIB DEFINITIONS ::= BEGIN

IMPORTS
        MODULE-IDENTITY, OBJECT-TYPE, Unsigned32 FROM SNMPv2-SMI
        MODULE-COMPLIANCE, OBJECT-GROUP FROM SNMPv2-CONF
        InetAddressType, InetAddress FROM INET-ADDRESS-MIB
        TEXTUAL-CONVENTION FROM SNMPv2-TC;

-- Module definition

  projectClearwater MODULE-IDENTITY
        LAST-UPDATED "201506220000Z"
        ORGANIZATION "Metaswitch"
        CONTACT-INFO
          "Metaswitch
           100 Church Street
           Enfield
           EN2 6BQ
           United Kingdom
           Tel: +44 20 8366 1177"
        DESCRIPTION  "This MIB module defines the Project
                      Clearwater statistics MIBs"

        REVISION      "201506220000Z" -- 22 Jun 2015
        DESCRIPTION   "Additional time scopes for Sprout/Bono stats"

        REVISION      "201411180000Z" -- 18 Nov 2014
        DESCRIPTION   "Addition of Memento statistics"

        REVISION      "201310102120Z" -- 10 Oct 2013
        DESCRIPTION   "Registration of initial global statistics"

        ::= { dataConnection 9 }

-- The object identifier subtree for the ProjectClearwater MIBs.

memberBody      OBJECT IDENTIFIER ::= { iso 2 }
gb              OBJECT IDENTIFIER ::= { memberBody 826 }
gbNational      OBJECT IDENTIFIER ::= { gb 0 }
gbNatCompany    OBJECT IDENTIFIER ::= { gbNational 1 }
dataConnection  OBJECT IDENTIFIER ::= { gbNatCompany 1578918 }

-- Module Compliance
projectClearwaterConformance OBJECT IDENTIFIER ::= { projectClearwater 0 }
projectClearwaterCompliance MODULE-COMPLIANCE
    STATUS current
    DESCRIPTION "Compilance statement for PROJECT-CLEARWATER-MIB"
    MODULE
    GROUP bonoGroup
    DESCRIPTION "The bonoGroup must be exposed by Bono nodes"
    GROUP sproutGroup
    DESCRIPTION "The sproutGroup must be exposed by Sprout nodes"
    GROUP homesteadGroup
    DESCRIPTION "The homesteadGroup must be exposed by Homestead nodes"
    GROUP callDiversionASGroup
    DESCRIPTION "The callDiversionASGroup must be exposed by Call Diversion AS nodes"
    GROUP mementoGroup
    DESCRIPTION "The mementoGroup must be exposed by Memento nodes"
    GROUP astaireGroup
    DESCRIPTION "The astaireGroup must be exposed by nodes running Astaire"
    GROUP chronosGroup
    DESCRIPTION "The chronosGroup must be exposed by nodes running Chronos"
    GROUP geminiGroup
    DESCRIPTION "The geminiGroup must be exposed by nodes running Gemini"
    ::= { projectClearwaterConformance 1 }
projectClearwaterObjectGroups OBJECT IDENTIFIER ::= { projectClearwater 1 }

-- Node roles
--
-- Note that ID 0 is used for the module compliance.
bono             OBJECT IDENTIFIER ::= { projectClearwater 2 }
sprout           OBJECT IDENTIFIER ::= { projectClearwater 3 }
homer            OBJECT IDENTIFIER ::= { projectClearwater 4 }
homestead        OBJECT IDENTIFIER ::= { projectClearwater 5 }
sipp             OBJECT IDENTIFIER ::= { projectClearwater 6 }
callDiversionAs  OBJECT IDENTIFIER ::= { projectClearwater 7 }
memento          OBJECT IDENTIFIER ::= { projectClearwater 8 }
astaire          OBJECT IDENTIFIER ::= { projectClearwater 9 }
chronos          OBJECT IDENTIFIER ::= { projectClearwater 10 }
gemini           OBJECT IDENTIFIER ::= { projectClearwater 11 }

RequestType ::= TEXTUAL-CONVENTION
    STATUS      current
    DESCRIPTION "Represents a type of SIP request."
    SYNTAX      INTEGER {
                scopeINVITE(0),
                scopeACK(1),
                scopeBYE(2),
                scopeCANCEL(3),
                scopeOPTIONS(4),
                scopeREGISTER(5),
                scopePRACK(6),
                scopeSUBSCRIBE(7),
                scopeNOTIFY(8),
                scopePUBLISH(9),
                scopeINFO(10),
                scopeREFER(11),
                scopeMESSAGE(12),
                scopeUPDATE(13),
                scopeOTHER(14)
                }

-- Bono entries

bonoConnectedClients OBJECT-TYPE
    SYNTAX      Unsigned32
    MAX-ACCESS  read-only
    STATUS      current
    DESCRIPTION "Current count of connected upstream clients.

                 This is calculated by counting the allocated
                 flow records and thus:

                  * Only counts clients if they have attempted
                    to register (either successfully or not)
                  * Multiple clients muxed onto a single connection
                    (e.g. behind a PBX) will be counted as one
                    client."
    ::= { bono 1 }

bonoLatencyTable OBJECT-TYPE
    SYNTAX SEQUENCE OF BonoLatencyEntry
    MAX-ACCESS not-accessible
    STATUS current
    DESCRIPTION "Latency of SIP requests handled by this Bono
                 over the given period.  Latency measured in
                 microseconds"
    ::= { bono 2 }

bonoLatencyEntry OBJECT-TYPE
    SYNTAX      BonoLatencyEntry
    MAX-ACCESS  not-accessible
    STATUS      current
    DESCRIPTION "The average, variance, LWM and HWM of SIP message
                 latency"
    INDEX       { bonoLatencyScope }
    ::= { bonoLatencyTable 1 }

BonoLatencyEntry ::= SEQUENCE
{
  bonoLatencyScope          INTEGER,
  bonoLatencyAverage        Unsigned32,
  bonoLatencyVariance       Unsigned32,
  bonoLatencyHWM            Unsigned32,
  bonoLatencyLWM            Unsigned32,
  bonoLatencyCount          Unsigned32
}

bonoLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { bonoLatencyEntry 1 }

bonoLatencyAverage OBJECT-TYPE
    SYNTAX      Unsigned32
    MAX-ACCESS  read-only
    STATUS      current
    DESCRIPTION "The average latency over the period."
    ::= { bonoLatencyEntry 2 }

bonoLatencyVariance OBJECT-TYPE
    SYNTAX      Unsigned32
    MAX-ACCESS  read-only
    STATUS      current
    DESCRIPTION "The variance of the latency over the period."
    ::= { bonoLatencyEntry 3 }

bonoLatencyHWM OBJECT-TYPE
    SYNTAX      Unsigned32
    MAX-ACCESS  read-only
    STATUS      current
    DESCRIPTION "The highest latency over the period."
    ::= { bonoLatencyEntry 4 }

bonoLatencyLWM OBJECT-TYPE
    SYNTAX      Unsigned32
    MAX-ACCESS  read-only
    STATUS      current
    DESCRIPTION "The lowest latency over the period."
    ::= { bonoLatencyEntry 5 }

bonoLatencyCount OBJECT-TYPE
    SYNTAX      Unsigned32
    MAX-ACCESS  read-only
    STATUS      current
    DESCRIPTION "The total requests over the period."
    ::= { bonoLatencyEntry 6 }

core OBJECT IDENTIFIER ::= { bono 3 }

bonoConnectedSproutsTable OBJECT-TYPE
    SYNTAX SEQUENCE OF BonoConnectedSproutsEntry
    MAX-ACCESS not-accessible
    STATUS current
    DESCRIPTION "Statistics for each connected upstream Sprout node"
    ::= { core 1 }

bonoConnectedSproutsEntry OBJECT-TYPE
    SYNTAX BonoConnectedSproutsEntry
    MAX-ACCESS not-accessible
    STATUS current
    DESCRIPTION "Statistics for a single connected upstream Sprout"
    INDEX { bonoSproutInetAddrType,
            bonoSproutInetAddr      }
    ::= { bonoConnectedSproutsTable 1 }

BonoConnectedSproutsEntry ::= SEQUENCE
{
  bonoSproutInetAddrType    InetAddressType,
  bonoSproutInetAddr        InetAddress,
  bonoSproutConnectionCount Unsigned32
}

bonoSproutInetAddrType OBJECT-TYPE
    SYNTAX      InetAddressType
    MAX-ACCESS  not-accessible
    STATUS      current
    DESCRIPTION "Inet address type of the upstream Sprout"
    ::= { bonoConnectedSproutsEntry 1 }

bonoSproutInetAddr OBJECT-TYPE
    SYNTAX      InetAddress (SIZE (1..16))
    MAX-ACCESS  not-accessible
    STATUS      current
    DESCRIPTION "Inet address of the upstream Sprout"
    ::= { bonoConnectedSproutsEntry 2 }

bonoSproutConnectionCount OBJECT-TYPE
    SYNTAX      Unsigned32
    MAX-ACCESS  read-only
    STATUS      current
    DESCRIPTION "Current count of TCP connections from Bono to the
                 Sprout node, may include connections in setting-
                 up state"
    ::= { bonoConnectedSproutsEntry 3 }

bonoIncomingRequestsTable OBJECT-TYPE
    SYNTAX SEQUENCE OF BonoIncomingRequestsEntry
    MAX-ACCESS not-accessible
    STATUS current
    DESCRIPTION "Total number of incoming requests handled by this Bono over
                 the given period."
    ::= { bono 4 }

bonoIncomingRequestsEntry OBJECT-TYPE
    SYNTAX      BonoIncomingRequestsEntry
    MAX-ACCESS  not-accessible
    STATUS      current
    DESCRIPTION "The total number of incoming requests"
    INDEX       { bonoIncomingRequestsScope }
    ::= { bonoIncomingRequestsTable 1 }

BonoIncomingRequestsEntry ::= SEQUENCE
{
  bonoIncomingRequestsScope          INTEGER,
  bonoIncomingRequestsCount          Unsigned32
}

bonoIncomingRequestsScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { bonoIncomingRequestsEntry 1 }

bonoIncomingRequestsCount OBJECT-TYPE
    SYNTAX      Unsigned32
    MAX-ACCESS  read-only
    STATUS      current
    DESCRIPTION "The total number of incoming requests over the period."
    ::= { bonoIncomingRequestsEntry 2 }

bonoRejectedOverloadTable OBJECT-TYPE
    SYNTAX SEQUENCE OF BonoRejectedOverloadEntry
    MAX-ACCESS not-accessible
    STATUS current
    DESCRIPTION "Total number of requests rejected due to overload by
                 this Bono over the given period."
    ::= { bono 5 }

bonoRejectedOverloadEntry OBJECT-TYPE
    SYNTAX      BonoRejectedOverloadEntry
    MAX-ACCESS  not-accessible
    STATUS      current
    DESCRIPTION "The total number of requests rejected due to overload"
    INDEX       { bonoRejectedOverloadScope }
    ::= { bonoRejectedOverloadTable 1 }

BonoRejectedOverloadEntry ::= SEQUENCE
{
  bonoRejectedOverloadScope          INTEGER,
  bonoRejectedOverloadCount          Unsigned32
}

bonoRejectedOverloadScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { bonoRejectedOverloadEntry 1 }

bonoRejectedOverloadCount OBJECT-TYPE
    SYNTAX      Unsigned32
    MAX-ACCESS  read-only
    STATUS      current
    DESCRIPTION "The total number of rejected requests due to overload over the
                 period."
    ::= { bonoRejectedOverloadEntry 2 }

bonoQueueSizeTable OBJECT-TYPE
    SYNTAX SEQUENCE OF BonoQueueSizeEntry
    MAX-ACCESS not-accessible
    STATUS current
    DESCRIPTION "Average request queue size for this Bono"
    ::= { bono 6 }

bonoQueueSizeEntry OBJECT-TYPE
    SYNTAX      BonoQueueSizeEntry
    MAX-ACCESS  not-accessible
    STATUS      current
    DESCRIPTION "The average, variance, LWM and HWM of request queue size"
    INDEX       { bonoQueueSizeScope }
    ::= { bonoQueueSizeTable 1 }

BonoQueueSizeEntry ::= SEQUENCE
{
  bonoQueueSizeScope          INTEGER,
  bonoQueueSizeAverage        Unsigned32,
  bonoQueueSizeVariance       Unsigned32,
  bonoQueueSizeHWM            Unsigned32,
  bonoQueueSizeLWM            Unsigned32,
  bonoQueueSizeCount          Unsigned32
}

bonoQueueSizeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { bonoQueueSizeEntry 1 }

bonoQueueSizeAverage OBJECT-TYPE
    SYNTAX      Unsigned32
    MAX-ACCESS  read-only
    STATUS      current
    DESCRIPTION "The average request queue size over the period."
    ::= { bonoQueueSizeEntry 2 }

bonoQueueSizeVariance OBJECT-TYPE
    SYNTAX      Unsigned32
    MAX-ACCESS  read-only
    STATUS      current
    DESCRIPTION "The variance of the queue size over the period."
    ::= { bonoQueueSizeEntry 3 }

bonoQueueSizeHWM OBJECT-TYPE
    SYNTAX      Unsigned32
    MAX-ACCESS  read-only
    STATUS      current
    DESCRIPTION "The highest queue size over the period."
    ::= { bonoQueueSizeEntry 4 }

bonoQueueSizeLWM OBJECT-TYPE
    SYNTAX      Unsigned32
    MAX-ACCESS  read-only
    STATUS      current
    DESCRIPTION "The lowest queue size over the period."
    ::= { bonoQueueSizeEntry 5 }

bonoQueueSizeCount OBJECT-TYPE
    SYNTAX      Unsigned32
    MAX-ACCESS  read-only
    STATUS      current
    DESCRIPTION "The total requests over the period."
    ::= { bonoQueueSizeEntry 6 }

bonoGroup OBJECT-GROUP
    OBJECTS {
      bonoConnectedClients,
      bonoLatencyAverage,
      bonoLatencyVariance,
      bonoLatencyHWM,
      bonoLatencyLWM,
      bonoLatencyCount,
      bonoSproutConnectionCount,
      bonoIncomingRequestsCount,
      bonoRejectedOverloadCount,
      bonoQueueSizeAverage,
      bonoQueueSizeVariance,
      bonoQueueSizeHWM,
      bonoQueueSizeLWM,
      bonoQueueSizeCount
    }
    STATUS      current
    DESCRIPTION "Statistics exposed by Bono"
    ::= { projectClearwaterObjectGroups 1 }

-- Sprout entries

sproutLatencyTable OBJECT-TYPE
    SYNTAX SEQUENCE OF SproutLatencyEntry
    MAX-ACCESS not-accessible
    STATUS current
    DESCRIPTION "Latency of SIP requests handled by this Sprout
                 over the given period.  Latency measured in
                 microseconds"
    ::= { sprout 1 }

sproutLatencyEntry OBJECT-TYPE
    SYNTAX      SproutLatencyEntry
    MAX-ACCESS  not-accessible
    STATUS      current
    DESCRIPTION "The average, variance, LWM and HWM of SIP message
                 latency"
    INDEX       { sproutLatencyScope }
    ::= { sproutLatencyTable 1 }

SproutLatencyEntry ::= SEQUENCE
{
  sproutLatencyScope          INTEGER,
  sproutLatencyAverage        Unsigned32,
  sproutLatencyVariance       Unsigned32,
  sproutLatencyHWM            Unsigned32,
  sproutLatencyLWM            Unsigned32,
  sproutLatencyCount          Unsigned32
}

sproutLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutLatencyEntry 1 }

sproutLatencyAverage OBJECT-TYPE
    SYNTAX      Unsigned32
    MAX-ACCESS  read-only
    STATUS      current
    DESCRIPTION "The average latency over the period."
    ::= { sproutLatencyEntry 2 }

sproutLatencyVariance OBJECT-TYPE
    SYNTAX      Unsigned32
    MAX-ACCESS  read-only
    STATUS      current
    DESCRIPTION "The variance of the latency over the period."
    ::= { sproutLatencyEntry 3 }

sproutLatencyHWM OBJECT-TYPE
    SYNTAX      Unsigned32
    MAX-ACCESS  read-only
    STATUS      current
    DESCRIPTION "The highest latency over the period."
    ::= { sproutLatencyEntry 4 }

sproutLatencyLWM OBJECT-TYPE
    SYNTAX      Unsigned32
    MAX-ACCESS  read-only
    STATUS      current
    DESCRIPTION "The lowest latency over the period."
    ::= { sproutLatencyEntry 5 }

sproutLatencyCount OBJECT-TYPE
    SYNTAX      Unsigned32
    MAX-ACCESS  read-only
    STATUS      current
    DESCRIPTION "The total requests over the period."
    ::= { sproutLatencyEntry 6 }

xdm OBJECT IDENTIFIER ::= { sprout 2 }

sproutConnectedHomersTable OBJECT-TYPE
    SYNTAX SEQUENCE OF SproutConnectedHomersEntry
    MAX-ACCESS not-accessible
    STATUS current
    DESCRIPTION "Statistics for each connected upstream Homer node"
    ::= { xdm 1 }

sproutConnectedHomersEntry OBJECT-TYPE
    SYNTAX SproutConnectedHomersEntry
    MAX-ACCESS not-accessible
    STATUS current
    DESCRIPTION "Statistics for a single connected upstream Homer"
    INDEX { sproutHomerInetAddrType,
            sproutHomerInetAddr      }
    ::= { sproutConnectedHomersTable 1 }

SproutConnectedHomersEntry ::= SEQUENCE
{
  sproutHomerInetAddrType    InetAddressType,
  sproutHomerInetAddr        InetAddress,
  sproutHomerConnectionCount Unsigned32
}

sproutHomerInetAddrType OBJECT-TYPE
    SYNTAX      InetAddressType
    MAX-ACCESS  not-accessible
    STATUS      current
    DESCRIPTION "Inet address type of the upstream Homer"
    ::= { sproutConnectedHomersEntry 1 }

sproutHomerInetAddr OBJECT-TYPE
    SYNTAX      InetAddress (SIZE (1..16))
    MAX-ACCESS  not-accessible
    STATUS      current
    DESCRIPTION "Inet address of the upstream Homer"
    ::= { sproutConnectedHomersEntry 2 }

sproutHomerConnectionCount OBJECT-TYPE
    SYNTAX      Unsigned32
    MAX-ACCESS  read-only
    STATUS      current
    DESCRIPTION "Current count of TCP connections from Sprout to the
                 Homer node, may include connections in setting-
                 up state"
    ::= { sproutConnectedHomersEntry 3 }

sproutHomerLatencyTable OBJECT-TYPE
    SYNTAX SEQUENCE OF SproutHomerLatencyEntry
    MAX-ACCESS not-accessible
    STATUS current
    DESCRIPTION "Latency of Homer requests made by this Sprout
                 over the given period.  Latency measured in
                 microseconds"
    ::= { xdm 2 }

sproutHomerLatencyEntry OBJECT-TYPE
    SYNTAX      SproutHomerLatencyEntry
    MAX-ACCESS  not-accessible
    STATUS      current
    DESCRIPTION "The average, variance, LWM and HWM of SIP message
                 latency"
    INDEX       { sproutHomerLatencyScope }
    ::= { sproutHomerLatencyTable 1 }

SproutHomerLatencyEntry ::= SEQUENCE
{
  sproutHomerLatencyScope          INTEGER,
  sproutHomerLatencyAverage        Unsigned32,
  sproutHomerLatencyVariance       Unsigned32,
  sproutHomerLatencyHWM            Unsigned32,
  sproutHomerLatencyLWM            Unsigned32,
  sproutHomerLatencyCount          Unsigned32
}

sproutHomerLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutHomerLatencyEntry 1 }

sproutHomerLatencyAverage OBJECT-TYPE
    SYNTAX      Unsigned32
    MAX-ACCESS  read-only
    STATUS      current
    DESCRIPTION "The average latency over the period."
    ::= { sproutHomerLatencyEntry 2 }

sproutHomerLatencyVariance OBJECT-TYPE
    SYNTAX      Unsigned32
    MAX-ACCESS  read-only
    STATUS      current
    DESCRIPTION "The variance of the latency over the period."
    ::= { sproutHomerLatencyEntry 3 }

sproutHomerLatencyHWM OBJECT-TYPE
    SYNTAX      Unsigned32
    MAX-ACCESS  read-only
    STATUS      current
    DESCRIPTION "The highest latency over the period."
    ::= { sproutHomerLatencyEntry 4 }

sproutHomerLatencyLWM OBJECT-TYPE
    SYNTAX      Unsigned32
    MAX-ACCESS  read-only
    STATUS      current
    DESCRIPTION "The lowest latency over the period."
    ::= { sproutHomerLatencyEntry 5 }

sproutHomerLatencyCount OBJECT-TYPE
    SYNTAX      Unsigned32
    MAX-ACCESS  read-only
    STATUS      current
    DESCRIPTION "The total requests over the period."
    ::= { sproutHomerLatencyEntry 6 }

hss OBJECT IDENTIFIER ::= { sprout 3 }

sproutConnectedHomesteadsTable OBJECT-TYPE
    SYNTAX SEQUENCE OF SproutConnectedHomesteadsEntry
    MAX-ACCESS not-accessible
    STATUS current
    DESCRIPTION "Statistics for each connected upstream Homestead node"
    ::= { hss 1 }

sproutConnectedHomesteadsEntry OBJECT-TYPE
    SYNTAX SproutConnectedHomesteadsEntry
    MAX-ACCESS not-accessible
    STATUS current
    DESCRIPTION "Statistics for a single connected upstream Homestead"
    INDEX { sproutHomesteadInetAddrType,
            sproutHomesteadInetAddr      }
    ::= { sproutConnectedHomesteadsTable 1 }

SproutConnectedHomesteadsEntry ::= SEQUENCE
{
  sproutHomesteadInetAddrType    InetAddressType,
  sproutHomesteadInetAddr        InetAddress,
  sproutHomesteadConnectionCount Unsigned32
}

sproutHomesteadInetAddrType OBJECT-TYPE
    SYNTAX      InetAddressType
    MAX-ACCESS  not-accessible
    STATUS      current
    DESCRIPTION "Inet address type of the upstream Homestead"
    ::= { sproutConnectedHomesteadsEntry 1 }

sproutHomesteadInetAddr OBJECT-TYPE
    SYNTAX      InetAddress (SIZE (1..16))
    MAX-ACCESS  not-accessible
    STATUS      current
    DESCRIPTION "Inet address of the upstream Homestead"
    ::= { sproutConnectedHomesteadsEntry 2 }

sproutHomesteadConnectionCount OBJECT-TYPE
    SYNTAX      Unsigned32
    MAX-ACCESS  read-only
    STATUS      current
    DESCRIPTION "Current count of TCP connections from Sprout to the
                 Homestead node, may include connections in setting-
                 up state"
    ::= { sproutConnectedHomesteadsEntry 3 }

sproutHomesteadLatencyTable OBJECT-TYPE
    SYNTAX SEQUENCE OF SproutHomesteadLatencyEntry
    MAX-ACCESS not-accessible
    STATUS current
    DESCRIPTION "Latency of Homestead requests made by this Sprout
                 over a the given period.  Latency measured in
                 microseconds"
    ::= { hss 2 }

sproutHomesteadLatencyEntry OBJECT-TYPE
    SYNTAX      SproutHomesteadLatencyEntry
    MAX-ACCESS  not-accessible
    STATUS      current
    DESCRIPTION "The average, variance, LWM and HWM of request
                 latency"
    INDEX       { sproutHomesteadLatencyScope }
    ::= { sproutHomesteadLatencyTable 1 }

SproutHomesteadLatencyEntry ::= SEQUENCE
{
  sproutHomesteadLatencyScope          INTEGER,
  sproutHomesteadLatencyAverage        Unsigned32,
  sproutHomesteadLatencyVariance       Unsigned32,
  sproutHomesteadLatencyHWM            Unsigned32,
  sproutHomesteadLatencyLWM            Unsigned32,
  sproutHomesteadLatencyCount          Unsigned32
}

sproutHomesteadLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutHomesteadLatencyEntry 1 }

sproutHomesteadLatencyAverage OBJECT-TYPE
    SYNTAX      Unsigned32
    MAX-ACCESS  read-only
    STATUS      current
    DESCRIPTION "The average latency over the period."
    ::= { sproutHomesteadLatencyEntry 2 }

sproutHomesteadLatencyVariance OBJECT-TYPE
    SYNTAX      Unsigned32
    MAX-ACCESS  read-only
    STATUS      current
    DESCRIPTION "The variance of the latency over the period."
    ::= { sproutHomesteadLatencyEntry 3 }

sproutHomesteadLatencyHWM OBJECT-TYPE
    SYNTAX      Unsigned32
    MAX-ACCESS  read-only
    STATUS      current
    DESCRIPTION "The highest latency over the period."
    ::= { sproutHomesteadLatencyEntry 4 }

sproutHomesteadLatencyLWM OBJECT-TYPE
    SYNTAX      Unsigned32
    MAX-ACCESS  read-only
    STATUS      current
    DESCRIPTION "The lowest latency over the period."
    ::= { sproutHomesteadLatencyEntry 5 }

sproutHomesteadLatencyCount OBJECT-TYPE
    SYNTAX      Unsigned32
    MAX-ACCESS  read-only
    STATUS      current
    DESCRIPTION "The total requests over the period."
    ::= { sproutHomesteadLatencyEntry 6 }

sproutMARLatencyTable OBJECT-TYPE
    SYNTAX SEQUENCE OF SproutMARLatencyEntry
    MAX-ACCESS not-accessible
    STATUS current
    DESCRIPTION "Latency of requests for MARs made by this Sprout
                 over the given period.  Latency measured in
                 microseconds"
    ::= { hss 3 }

sproutMARLatencyEntry OBJECT-TYPE
    SYNTAX      SproutMARLatencyEntry
    MAX-ACCESS  not-accessible
    STATUS      current
    DESCRIPTION "The average, variance, LWM and HWM of request
                 latency"
    INDEX       { sproutMARLatencyScope }
    ::= { sproutMARLatencyTable 1 }

SproutMARLatencyEntry ::= SEQUENCE
{
  sproutMARLatencyScope          INTEGER,
  sproutMARLatencyAverage        Unsigned32,
  sproutMARLatencyVariance       Unsigned32,
  sproutMARLatencyHWM            Unsigned32,
  sproutMARLatencyLWM            Unsigned32,
  sproutMARLatencyCount          Unsigned32
}

sproutMARLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutMARLatencyEntry 1 }

sproutMARLatencyAverage OBJECT-TYPE
    SYNTAX      Unsigned32
    MAX-ACCESS  read-only
    STATUS      current
    DESCRIPTION "The average latency over the period."
    ::= { sproutMARLatencyEntry 2 }

sproutMARLatencyVariance OBJECT-TYPE
    SYNTAX      Unsigned32
    MAX-ACCESS  read-only
    STATUS      current
    DESCRIPTION "The variance of the latency over the period."
    ::= { sproutMARLatencyEntry 3 }

sproutMARLatencyHWM OBJECT-TYPE
    SYNTAX      Unsigned32
    MAX-ACCESS  read-only
    STATUS      current
    DESCRIPTION "The highest latency over the period."
    ::= { sproutMARLatencyEntry 4 }

sproutMARLatencyLWM OBJECT-TYPE
    SYNTAX      Unsigned32
    MAX-ACCESS  read-only
    STATUS      current
    DESCRIPTION "The lowest latency over the period."
    ::= { sproutMARLatencyEntry 5 }

sproutMARLatencyCount OBJECT-TYPE
    SYNTAX      Unsigned32
    MAX-ACCESS  read-only
    STATUS      current
    DESCRIPTION "The total requests over the period."
    ::= { sproutMARLatencyEntry 6 }

sproutSARLatencyTable OBJECT-TYPE
    SYNTAX SEQUENCE OF SproutSARLatencyEntry
    MAX-ACCESS not-accessible
    STATUS current
    DESCRIPTION "Latency of requests for SARs made by this Sprout
                 over the given period.  Latency measured in
                 microseconds"
    ::= { hss 4 }

sproutSARLatencyEntry OBJECT-TYPE
    SYNTAX      SproutSARLatencyEntry
    MAX-ACCESS  not-accessible
    STATUS      current
    DESCRIPTION "The average, variance, LWM and HWM of request
                 latency"
    INDEX       { sproutSARLatencyScope }
    ::= { sproutSARLatencyTable 1 }

SproutSARLatencyEntry ::= SEQUENCE
{
  sproutSARLatencyScope          INTEGER,
  sproutSARLatencyAverage        Unsigned32,
  sproutSARLatencyVariance       Unsigned32,
  sproutSARLatencyHWM            Unsigned32,
  sproutSARLatencyLWM            Unsigned32,
  sproutSARLatencyCount          Unsigned32
}

sproutSARLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSARLatencyEntry 1 }

sproutSARLatencyAverage OBJECT-TYPE
    SYNTAX      Unsigned32
    MAX-ACCESS  read-only
    STATUS      current
    DESCRIPTION "The average latency over the period."
    ::= { sproutSARLatencyEntry 2 }

sproutSARLatencyVariance OBJECT-TYPE
    SYNTAX      Unsigned32
    MAX-ACCESS  read-only
    STATUS      current
    DESCRIPTION "The variance of the latency over the period."
    ::= { sproutSARLatencyEntry 3 }

sproutSARLatencyHWM OBJECT-TYPE
    SYNTAX      Unsigned32
    MAX-ACCESS  read-only
    STATUS      current
    DESCRIPTION "The highest latency over the period."
    ::= { sproutSARLatencyEntry 4 }

sproutSARLatencyLWM OBJECT-TYPE
    SYNTAX      Unsigned32
    MAX-ACCESS  read-only
    STATUS      current
    DESCRIPTION "The lowest latency over the period."
    ::= { sproutSARLatencyEntry 5 }

sproutSARLatencyCount OBJECT-TYPE
    SYNTAX      Unsigned32
    MAX-ACCESS  read-only
    STATUS      current
    DESCRIPTION "The total requests over the period."
    ::= { sproutSARLatencyEntry 6 }

sproutUARLatencyTable OBJECT-TYPE
    SYNTAX SEQUENCE OF SproutUARLatencyEntry
    MAX-ACCESS not-accessible
    STATUS current
    DESCRIPTION "Latency of requests for user authentication made by this Sprout
                 over the given period.  Latency measured in
                 microseconds"
    ::= { hss 5 }

sproutUARLatencyEntry OBJECT-TYPE
    SYNTAX      SproutUARLatencyEntry
    MAX-ACCESS  not-accessible
    STATUS      current
    DESCRIPTION "The average, variance, LWM and HWM of request
                 latency"
    INDEX       { sproutUARLatencyScope }
    ::= { sproutUARLatencyTable 1 }

SproutUARLatencyEntry ::= SEQUENCE
{
  sproutUARLatencyScope          INTEGER,
  sproutUARLatencyAverage        Unsigned32,
  sproutUARLatencyVariance       Unsigned32,
  sproutUARLatencyHWM            Unsigned32,
  sproutUARLatencyLWM            Unsigned32,
  sproutUARLatencyCount          Unsigned32
}

sproutUARLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutUARLatencyEntry 1 }

sproutUARLatencyAverage OBJECT-TYPE
    SYNTAX      Unsigned32
    MAX-ACCESS  read-only
    STATUS      current
    DESCRIPTION "The average latency over the period."
    ::= { sproutUARLatencyEntry 2 }

sproutUARLatencyVariance OBJECT-TYPE
    SYNTAX      Unsigned32
    MAX-ACCESS  read-only
    STATUS      current
    DESCRIPTION "The variance of the latency over the period."
    ::= { sproutUARLatencyEntry 3 }

sproutUARLatencyHWM OBJECT-TYPE
    SYNTAX      Unsigned32
    MAX-ACCESS  read-only
    STATUS      current
    DESCRIPTION "The highest latency over the period."
    ::= { sproutUARLatencyEntry 4 }

sproutUARLatencyLWM OBJECT-TYPE
    SYNTAX      Unsigned32
    MAX-ACCESS  read-only
    STATUS      current
    DESCRIPTION "The lowest latency over the period."
    ::= { sproutUARLatencyEntry 5 }

sproutUARLatencyCount OBJECT-TYPE
    SYNTAX      Unsigned32
    MAX-ACCESS  read-only
    STATUS      current
    DESCRIPTION "The total requests over the period."
    ::= { sproutUARLatencyEntry 6 }

sproutLIRLatencyTable OBJECT-TYPE
    SYNTAX SEQUENCE OF SproutLIRLatencyEntry
    MAX-ACCESS not-accessible
    STATUS current
    DESCRIPTION "Latency of location requests made by this Sprout
                 over the given period.  Latency measured in
                 microseconds"
    ::= { hss 6 }

sproutLIRLatencyEntry OBJECT-TYPE
    SYNTAX      SproutLIRLatencyEntry
    MAX-ACCESS  not-accessible
    STATUS      current
    DESCRIPTION "The average, variance, LWM and HWM of request
                 latency"
    INDEX       { sproutLIRLatencyScope }
    ::= { sproutLIRLatencyTable 1 }

SproutLIRLatencyEntry ::= SEQUENCE
{
  sproutLIRLatencyScope          INTEGER,
  sproutLIRLatencyAverage        Unsigned32,
  sproutLIRLatencyVariance       Unsigned32,
  sproutLIRLatencyHWM            Unsigned32,
  sproutLIRLatencyLWM            Unsigned32,
  sproutLIRLatencyCount          Unsigned32
}

sproutLIRLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutLIRLatencyEntry 1 }

sproutLIRLatencyAverage OBJECT-TYPE
    SYNTAX      Unsigned32
    MAX-ACCESS  read-only
    STATUS      current
    DESCRIPTION "The average latency over the period."
    ::= { sproutLIRLatencyEntry 2 }

sproutLIRLatencyVariance OBJECT-TYPE
    SYNTAX      Unsigned32
    MAX-ACCESS  read-only
    STATUS      current
    DESCRIPTION "The variance of the latency over the period."
    ::= { sproutLIRLatencyEntry 3 }

sproutLIRLatencyHWM OBJECT-TYPE
    SYNTAX      Unsigned32
    MAX-ACCESS  read-only
    STATUS      current
    DESCRIPTION "The highest latency over the period."
    ::= { sproutLIRLatencyEntry 4 }

sproutLIRLatencyLWM OBJECT-TYPE
    SYNTAX      Unsigned32
    MAX-ACCESS  read-only
    STATUS      current
    DESCRIPTION "The lowest latency over the period."
    ::= { sproutLIRLatencyEntry 5 }

sproutLIRLatencyCount OBJECT-TYPE
    SYNTAX      Unsigned32
    MAX-ACCESS  read-only
    STATUS      current
    DESCRIPTION "The total requests over the period."
    ::= { sproutLIRLatencyEntry 6 }

sproutIncomingRequestsTable OBJECT-TYPE
    SYNTAX SEQUENCE OF SproutIncomingRequestsEntry
    MAX-ACCESS not-accessible
    STATUS current
    DESCRIPTION "Total number of incoming requests handled by this Sprout over
                 the given period."
    ::= { sprout 6 }

sproutIncomingRequestsEntry OBJECT-TYPE
    SYNTAX      SproutIncomingRequestsEntry
    MAX-ACCESS  not-accessible
    STATUS      current
    DESCRIPTION "The total number of incoming requests"
    INDEX       { sproutIncomingRequestsScope }
    ::= { sproutIncomingRequestsTable 1 }

SproutIncomingRequestsEntry ::= SEQUENCE
{
  sproutIncomingRequestsScope          INTEGER,
  sproutIncomingRequestsCount          Unsigned32
}

sproutIncomingRequestsScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutIncomingRequestsEntry 1 }

sproutIncomingRequestsCount OBJECT-TYPE
    SYNTAX      Unsigned32
    MAX-ACCESS  read-only
    STATUS      current
    DESCRIPTION "The total number of incoming requests over the period."
    ::= { sproutIncomingRequestsEntry 2 }

sproutRejectedOverloadTable OBJECT-TYPE
    SYNTAX SEQUENCE OF SproutRejectedOverloadEntry
    MAX-ACCESS not-accessible
    STATUS current
    DESCRIPTION "Total number of requests rejected due to overload by
                 this Sprout over the given period."
    ::= { sprout 7 }

sproutRejectedOverloadEntry OBJECT-TYPE
    SYNTAX      SproutRejectedOverloadEntry
    MAX-ACCESS  not-accessible
    STATUS      current
    DESCRIPTION "The total number of requests rejected due to overload"
    INDEX       { sproutRejectedOverloadScope }
    ::= { sproutRejectedOverloadTable 1 }

SproutRejectedOverloadEntry ::= SEQUENCE
{
  sproutRejectedOverloadScope          INTEGER,
  sproutRejectedOverloadCount          Unsigned32
}

sproutRejectedOverloadScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutRejectedOverloadEntry 1 }

sproutRejectedOverloadCount OBJECT-TYPE
    SYNTAX      Unsigned32
    MAX-ACCESS  read-only
    STATUS      current
    DESCRIPTION "The total number of rejected requests due to overload over the
                 period."
    ::= { sproutRejectedOverloadEntry 2 }

sproutQueueSizeTable OBJECT-TYPE
    SYNTAX SEQUENCE OF SproutQueueSizeEntry
    MAX-ACCESS not-accessible
    STATUS current
    DESCRIPTION "Average request queue size for this Sprout"
    ::= { sprout 8 }

sproutQueueSizeEntry OBJECT-TYPE
    SYNTAX      SproutQueueSizeEntry
    MAX-ACCESS  not-accessible
    STATUS      current
    DESCRIPTION "The average, variance, LWM and HWM of request queue size"
    INDEX       { sproutQueueSizeScope }
    ::= { sproutQueueSizeTable 1 }

SproutQueueSizeEntry ::= SEQUENCE
{
  sproutQueueSizeScope          INTEGER,
  sproutQueueSizeAverage        Unsigned32,
  sproutQueueSizeVariance       Unsigned32,
  sproutQueueSizeHWM            Unsigned32,
  sproutQueueSizeLWM            Unsigned32,
  sproutQueueSizeCount          Unsigned32
}

sproutQueueSizeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutQueueSizeEntry 1 }

sproutQueueSizeAverage OBJECT-TYPE
    SYNTAX      Unsigned32
    MAX-ACCESS  read-only
    STATUS      current
    DESCRIPTION "The average request queue size over the period."
    ::= { sproutQueueSizeEntry 2 }

sproutQueueSizeVariance OBJECT-TYPE
    SYNTAX      Unsigned32
    MAX-ACCESS  read-only
    STATUS      current
    DESCRIPTION "The variance of the queue size over the period."
    ::= { sproutQueueSizeEntry 3 }

sproutQueueSizeHWM OBJECT-TYPE
    SYNTAX      Unsigned32
    MAX-ACCESS  read-only
    STATUS      current
    DESCRIPTION "The highest queue size over the period."
    ::= { sproutQueueSizeEntry 4 }

sproutQueueSizeLWM OBJECT-TYPE
    SYNTAX      Unsigned32
    MAX-ACCESS  read-only
    STATUS      current
    DESCRIPTION "The lowest queue size over the period."
    ::= { sproutQueueSizeEntry 5 }

sproutQueueSizeCount OBJECT-TYPE
    SYNTAX      Unsigned32
    MAX-ACCESS  read-only
    STATUS      current
    DESCRIPTION "The total requests over the period."
    ::= { sproutQueueSizeEntry 6 }

sproutInitialRegistrationTable OBJECT-TYPE
    SYNTAX SEQUENCE OF SproutInitialRegistrationEntry
    MAX-ACCESS not-accessible
    STATUS current
    DESCRIPTION "Counts the number of attempts, successes and failures
                 of initial registrations"
    ::= { sprout 9 }

sproutInitialRegistrationEntry OBJECT-TYPE
    SYNTAX      SproutInitialRegistrationEntry
    MAX-ACCESS  not-accessible
    STATUS      current
    DESCRIPTION "The number of attempts, successes and failures for
                 initial registrations"
    INDEX       { sproutInitialRegistrationScope }
    ::= { sproutInitialRegistrationTable 1 }

SproutInitialRegistrationEntry ::= SEQUENCE
{
  sproutInitialRegistrationScope          INTEGER,
  sproutInitialRegistrationAttempts       Unsigned32,
  sproutInitialRegistrationSuccesses      Unsigned32,
  sproutInitialRegistrationFailures       Unsigned32
}

sproutInitialRegistrationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutInitialRegistrationEntry 1 }

sproutInitialRegistrationAttempts OBJECT-TYPE
    SYNTAX      Unsigned32
    MAX-ACCESS  read-only
    STATUS      current
    DESCRIPTION "The number of initial registration attempts over the period."
    ::= { sproutInitialRegistrationEntry 2 }

sproutInitialRegistrationSuccesses OBJECT-TYPE
    SYNTAX      Unsigned32
    MAX-ACCESS  read-only
    STATUS      current
    DESCRIPTION "The number of initial registration successes over the period."
    ::= { sproutInitialRegistrationEntry 3 }

sproutInitialRegistrationFailures OBJECT-TYPE
    SYNTAX      Unsigned32
    MAX-ACCESS  read-only
    STATUS      current
    DESCRIPTION "The number of initial registration failures over the period."
    ::= { sproutInitialRegistrationEntry 4 }

sproutReRegistrationTable OBJECT-TYPE
    SYNTAX SEQUENCE OF SproutReRegistrationEntry
    MAX-ACCESS not-accessible
    STATUS current
    DESCRIPTION "Counts the number of attempts, successes and failures
                 of re-registrations"
    ::= { sprout 10 }

sproutReRegistrationEntry OBJECT-TYPE
    SYNTAX      SproutReRegistrationEntry
    MAX-ACCESS  not-accessible
    STATUS      current
    DESCRIPTION "The number of attempts, successes and failures for
                 re-registrations"
    INDEX       { sproutReRegistrationScope }
    ::= { sproutReRegistrationTable 1 }

SproutReRegistrationEntry ::= SEQUENCE
{
  sproutReRegistrationScope          INTEGER,
  sproutReRegistrationAttempts       Unsigned32,
  sproutReRegistrationSuccesses      Unsigned32,
  sproutReRegistrationFailures       Unsigned32
}

sproutReRegistrationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutReRegistrationEntry 1 }

sproutReRegistrationAttempts OBJECT-TYPE
    SYNTAX      Unsigned32
    MAX-ACCESS  read-only
    STATUS      current
    DESCRIPTION "The number of re-registration attempts over the period."
    ::= { sproutReRegistrationEntry 2 }

sproutReRegistrationSuccesses OBJECT-TYPE
    SYNTAX      Unsigned32
    MAX-ACCESS  read-only
    STATUS      current
    DESCRIPTION "The number of re-registration successes over the period."
    ::= { sproutReRegistrationEntry 3 }

sproutReRegistrationFailures OBJECT-TYPE
    SYNTAX      Unsigned32
    MAX-ACCESS  read-only
    STATUS      current
    DESCRIPTION "The number of re-registration failures over the period."
    ::= { sproutReRegistrationEntry 4 }

sproutDeRegistrationTable OBJECT-TYPE
    SYNTAX SEQUENCE OF SproutDeRegistrationEntry
    MAX-ACCESS not-accessible
    STATUS current
    DESCRIPTION "Counts the number of attempts, successes and failures
                 of de-registrations"
    ::= { sprout 11 }

sproutDeRegistrationEntry OBJECT-TYPE
    SYNTAX      SproutDeRegistrationEntry
    MAX-ACCESS  not-accessible
    STATUS      current
    DESCRIPTION "The number of attempts, successes and failures for
                 de-registrations"
    INDEX       { sproutDeRegistrationScope }
    ::= { sproutDeRegistrationTable 1 }

SproutDeRegistrationEntry ::= SEQUENCE
{
  sproutDeRegistrationScope          INTEGER,
  sproutDeRegistrationAttempts       Unsigned32,
  sproutDeRegistrationSuccesses      Unsigned32,
  sproutDeRegistrationFailures       Unsigned32
}

sproutDeRegistrationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutDeRegistrationEntry 1 }

sproutDeRegistrationAttempts OBJECT-TYPE
    SYNTAX      Unsigned32
    MAX-ACCESS  read-only
    STATUS      current
    DESCRIPTION "The number of de-registration attempts over the period."
    ::= { sproutDeRegistrationEntry 2 }

sproutDeRegistrationSuccesses OBJECT-TYPE
    SYNTAX      Unsigned32
    MAX-ACCESS  read-only
    STATUS      current
    DESCRIPTION "The number of de-registration successes over the period."
    ::= { sproutDeRegistrationEntry 3 }

sproutDeRegistrationFailures OBJECT-TYPE
    SYNTAX      Unsigned32
    MAX-ACCESS  read-only
    STATUS      current
    DESCRIPTION "The number of de-registration failures over the period."
    ::= { sproutDeRegistrationEntry 4 }

sproutThirdPartyInitialRegistrationTable OBJECT-TYPE
    SYNTAX SEQUENCE OF SproutThirdPartyInitialRegistrationEntry
    MAX-ACCESS not-accessible
    STATUS current
    DESCRIPTION "Counts the number of attempts, successes and failures
                 of third-party initial registrations"
    ::= { sprout 12 }

sproutThirdPartyInitialRegistrationEntry OBJECT-TYPE
    SYNTAX      SproutThirdPartyInitialRegistrationEntry
    MAX-ACCESS  not-accessible
    STATUS      current
    DESCRIPTION "The number of attempts, successes and failures for
                 third-party initial registrations"
    INDEX       { sproutThirdPartyInitialRegistrationScope }
    ::= { sproutThirdPartyInitialRegistrationTable 1 }

SproutThirdPartyInitialRegistrationEntry ::= SEQUENCE
{
  sproutThirdPartyInitialRegistrationScope          INTEGER,
  sproutThirdPartyInitialRegistrationAttempts       Unsigned32,
  sproutThirdPartyInitialRegistrationSuccesses      Unsigned32,
  sproutThirdPartyInitialRegistrationFailures       Unsigned32
}

sproutThirdPartyInitialRegistrationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutThirdPartyInitialRegistrationEntry 1 }

sproutThirdPartyInitialRegistrationAttempts OBJECT-TYPE
    SYNTAX      Unsigned32
    MAX-ACCESS  read-only
    STATUS      current
    DESCRIPTION "The number of third-party initial registration attempts over
the period."
    ::= { sproutThirdPartyInitialRegistrationEntry 2 }

sproutThirdPartyInitialRegistrationSuccesses OBJECT-TYPE
    SYNTAX      Unsigned32
    MAX-ACCESS  read-only
    STATUS      current
    DESCRIPTION "The number of third-party initial registration successes over
                 the period."
    ::= { sproutThirdPartyInitialRegistrationEntry 3 }

sproutThirdPartyInitialRegistrationFailures OBJECT-TYPE
    SYNTAX      Unsigned32
    MAX-ACCESS  read-only
    STATUS      current
    DESCRIPTION "The number of third-party initial registration failures over
                 the period."
    ::= { sproutThirdPartyInitialRegistrationEntry 4 }

sproutThirdPartyReRegistrationTable OBJECT-TYPE
    SYNTAX SEQUENCE OF SproutThirdPartyReRegistrationEntry
    MAX-ACCESS not-accessible
    STATUS current
    DESCRIPTION "Counts the number of attempts, successes and failures
                 of third-party re-registrations"
    ::= { sprout 13 }

sproutThirdPartyReRegistrationEntry OBJECT-TYPE
    SYNTAX      SproutThirdPartyReRegistrationEntry
    MAX-ACCESS  not-accessible
    STATUS      current
    DESCRIPTION "The number of attempts, successes and failures for
                 third-party re-registrations"
    INDEX       { sproutThirdPartyReRegistrationScope }
    ::= { sproutThirdPartyReRegistrationTable 1 }

SproutThirdPartyReRegistrationEntry ::= SEQUENCE
{
  sproutThirdPartyReRegistrationScope          INTEGER,
  sproutThirdPartyReRegistrationAttempts       Unsigned32,
  sproutThirdPartyReRegistrationSuccesses      Unsigned32,
  sproutThirdPartyReRegistrationFailures       Unsigned32
}

sproutThirdPartyReRegistrationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutThirdPartyReRegistrationEntry 1 }

sproutThirdPartyReRegistrationAttempts OBJECT-TYPE
    SYNTAX      Unsigned32
    MAX-ACCESS  read-only
    STATUS      current
    DESCRIPTION "The number of third-party re-registration attempts over the
period."
    ::= { sproutThirdPartyReRegistrationEntry 2 }

sproutThirdPartyReRegistrationSuccesses OBJECT-TYPE
    SYNTAX      Unsigned32
    MAX-ACCESS  read-only
    STATUS      current
    DESCRIPTION "The number of third-party re-registration successes over the
period."
    ::= { sproutThirdPartyReRegistrationEntry 3 }

sproutThirdPartyReRegistrationFailures OBJECT-TYPE
    SYNTAX      Unsigned32
    MAX-ACCESS  read-only
    STATUS      current
    DESCRIPTION "The number of third-party re-registration failures over the
period."
    ::= { sproutThirdPartyReRegistrationEntry 4 }

sproutThirdPartyDeRegistrationTable OBJECT-TYPE
    SYNTAX SEQUENCE OF SproutThirdPartyDeRegistrationEntry
    MAX-ACCESS not-accessible
    STATUS current
    DESCRIPTION "Counts the number of attempts, successes and failures
                 of third-party de-registrations"
    ::= { sprout 14 }

sproutThirdPartyDeRegistrationEntry OBJECT-TYPE
    SYNTAX      SproutThirdPartyDeRegistrationEntry
    MAX-ACCESS  not-accessible
    STATUS      current
    DESCRIPTION "The number of attempts, successes and failures for
                 third-party de-registrations"
    INDEX       { sproutThirdPartyDeRegistrationScope }
    ::= { sproutThirdPartyDeRegistrationTable 1 }

SproutThirdPartyDeRegistrationEntry ::= SEQUENCE
{
  sproutThirdPartyDeRegistrationScope          INTEGER,
  sproutThirdPartyDeRegistrationAttempts       Unsigned32,
  sproutThirdPartyDeRegistrationSuccesses      Unsigned32,
  sproutThirdPartyDeRegistrationFailures       Unsigned32
}

sproutThirdPartyDeRegistrationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutThirdPartyDeRegistrationEntry 1 }

sproutThirdPartyDeRegistrationAttempts OBJECT-TYPE
    SYNTAX      Unsigned32
    MAX-ACCESS  read-only
    STATUS      current
    DESCRIPTION "The number of third-party de-registration attempts over the
period."
    ::= { sproutThirdPartyDeRegistrationEntry 2 }

sproutThirdPartyDeRegistrationSuccesses OBJECT-TYPE
    SYNTAX      Unsigned32
    MAX-ACCESS  read-only
    STATUS      current
    DESCRIPTION "The number of third-party de-registration successes over the
period."
    ::= { sproutThirdPartyDeRegistrationEntry 3 }

sproutThirdPartyDeRegistrationFailures OBJECT-TYPE
    SYNTAX      Unsigned32
    MAX-ACCESS  read-only
    STATUS      current
    DESCRIPTION "The number of third-party de-registration failures over the
period."
    ::= { sproutThirdPartyDeRegistrationEntry 4 }

sproutSIPDigestAuthenticationTable OBJECT-TYPE
    SYNTAX SEQUENCE OF SproutSIPDigestAuthenticationEntry
    MAX-ACCESS not-accessible
    STATUS current
    DESCRIPTION "Counts the number of attempts, successes and failures
                 of SIP digest authentications on register requests"
    ::= { sprout 15 }

sproutSIPDigestAuthenticationEntry OBJECT-TYPE
    SYNTAX      SproutSIPDigestAuthenticationEntry
    MAX-ACCESS  not-accessible
    STATUS      current
    DESCRIPTION "The number of attempts, successes and failures for
                 SIP digest authentications on register requests"
    INDEX       { sproutSIPDigestAuthenticationScope }
    ::= { sproutSIPDigestAuthenticationTable 1 }

SproutSIPDigestAuthenticationEntry ::= SEQUENCE
{
  sproutSIPDigestAuthenticationScope          INTEGER,
  sproutSIPDigestAuthenticationAttempts       Unsigned32,
  sproutSIPDigestAuthenticationSuccesses      Unsigned32,
  sproutSIPDigestAuthenticationFailures       Unsigned32
}

sproutSIPDigestAuthenticationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSIPDigestAuthenticationEntry 1 }

sproutSIPDigestAuthenticationAttempts OBJECT-TYPE
    SYNTAX      Unsigned32
    MAX-ACCESS  read-only
    STATUS      current
    DESCRIPTION "The number of SIP digest authentication attempts on register
                 requests over the period."
    ::= { sproutSIPDigestAuthenticationEntry 2 }

sproutSIPDigestAuthenticationSuccesses OBJECT-TYPE
    SYNTAX      Unsigned32
    MAX-ACCESS  read-only
    STATUS      current
    DESCRIPTION "The number of SIP digest authentication successes on register
                 requests over the period."
    ::= { sproutSIPDigestAuthenticationEntry 3 }

sproutSIPDigestAuthenticationFailures OBJECT-TYPE
    SYNTAX      Unsigned32
    MAX-ACCESS  read-only
    STATUS      current
    DESCRIPTION "The number of SIP digest authentication failures on register
                 requests over the period."
    ::= { sproutSIPDigestAuthenticationEntry 4 }

sproutAKAAuthenticationTable OBJECT-TYPE
    SYNTAX SEQUENCE OF SproutAKAAuthenticationEntry
    MAX-ACCESS not-accessible
    STATUS current
    DESCRIPTION "Counts the number of attempts, successes and failures
                 of AKA authentications on register requests"
    ::= { sprout 16 }

sproutAKAAuthenticationEntry OBJECT-TYPE
    SYNTAX      SproutAKAAuthenticationEntry
    MAX-ACCESS  not-accessible
    STATUS      current
    DESCRIPTION "The number of attempts, successes and failures for
                 AKA authentications on register requests"
    INDEX       { sproutAKAAuthenticationScope }
    ::= { sproutAKAAuthenticationTable 1 }

SproutAKAAuthenticationEntry ::= SEQUENCE
{
  sproutAKAAuthenticationScope          INTEGER,
  sproutAKAAuthenticationAttempts       Unsigned32,
  sproutAKAAuthenticationSuccesses      Unsigned32,
  sproutAKAAuthenticationFailures       Unsigned32
}

sproutAKAAuthenticationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutAKAAuthenticationEntry 1 }

sproutAKAAuthenticationAttempts OBJECT-TYPE
    SYNTAX      Unsigned32
    MAX-ACCESS  read-only
    STATUS      current
    DESCRIPTION "The number of AKA authentication attempts on register
                 requests over the period."
    ::= { sproutAKAAuthenticationEntry 2 }

sproutAKAAuthenticationSuccesses OBJECT-TYPE
    SYNTAX      Unsigned32
    MAX-ACCESS  read-only
    STATUS      current
    DESCRIPTION "The number of AKA authentication successes on register
                 requests over the period."
    ::= { sproutAKAAuthenticationEntry 3 }

sproutAKAAuthenticationFailures OBJECT-TYPE
    SYNTAX      Unsigned32
    MAX-ACCESS  read-only
    STATUS      current
    DESCRIPTION "The number of AKA authentication failures on register
                 requests over the period."
    ::= { sproutAKAAuthenticationEntry 4 }

sproutNonRegisterAuthenticationTable OBJECT-TYPE
    SYNTAX SEQUENCE OF SproutNonRegisterAuthenticationEntry
    MAX-ACCESS not-accessible
    STATUS current
    DESCRIPTION "Counts the number of attempts, successes and failures
                 of non-register authentication requests"
    ::= { sprout 17 }

sproutNonRegisterAuthenticationEntry OBJECT-TYPE
    SYNTAX      SproutNonRegisterAuthenticationEntry
    MAX-ACCESS  not-accessible
    STATUS      current
    DESCRIPTION "The number of attempts, successes and failures for
                 non-register authentication requests"
    INDEX       { sproutNonRegisterAuthenticationScope }
    ::= { sproutNonRegisterAuthenticationTable 1 }

SproutNonRegisterAuthenticationEntry ::= SEQUENCE
{
  sproutNonRegisterAuthenticationScope          INTEGER,
  sproutNonRegisterAuthenticationAttempts       Unsigned32,
  sproutNonRegisterAuthenticationSuccesses      Unsigned32,
  sproutNonRegisterAuthenticationFailures       Unsigned32
}

sproutNonRegisterAuthenticationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutNonRegisterAuthenticationEntry 1 }

sproutNonRegisterAuthenticationAttempts OBJECT-TYPE
    SYNTAX      Unsigned32
    MAX-ACCESS  read-only
    STATUS      current
    DESCRIPTION "The number of non-register authentication attempts on register
                 requests over the period."
    ::= { sproutNonRegisterAuthenticationEntry 2 }

sproutNonRegisterAuthenticationSuccesses OBJECT-TYPE
    SYNTAX      Unsigned32
    MAX-ACCESS  read-only
    STATUS      current
    DESCRIPTION "The number of non-register authentication successes on register
                 requests over the period."
    ::= { sproutNonRegisterAuthenticationEntry 3 }

sproutNonRegisterAuthenticationFailures OBJECT-TYPE
    SYNTAX      Unsigned32
    MAX-ACCESS  read-only
    STATUS      current
    DESCRIPTION "The number of non-register authentication failures on register
                 requests over the period."
    ::= { sproutNonRegisterAuthenticationEntry 4 }

sproutICSCFIncomingSIPTransactionsTable OBJECT-TYPE
    SYNTAX SEQUENCE OF SproutICSCFIncomingSIPTransactionsEntry
    MAX-ACCESS not-accessible
    STATUS current
    DESCRIPTION "Counts the number of attempts, successes and failures
                 of incoming SIP transactions for the ICSCF"
    ::= { sprout 18 }

sproutICSCFIncomingSIPTransactionsEntry OBJECT-TYPE
    SYNTAX      SproutICSCFIncomingSIPTransactionsEntry
    MAX-ACCESS  not-accessible
    STATUS      current
    DESCRIPTION "The number of attempts, successes and failures for
                 incoming SIP transactions for the ICSCF"
    INDEX       { sproutICSCFIncomingSIPTransactionsTimeScope,
                  sproutICSCFIncomingSIPTransactionsRequestScope }
    ::= { sproutICSCFIncomingSIPTransactionsTable 1 }

SproutICSCFIncomingSIPTransactionsEntry ::= SEQUENCE
{
  sproutICSCFIncomingSIPTransactionsTimeScope      INTEGER,
  sproutICSCFIncomingSIPTransactionsRequestScope   INTEGER,
  sproutICSCFIncomingSIPTransactionsAttempts       Unsigned32,
  sproutICSCFIncomingSIPTransactionsSuccesses      Unsigned32,
  sproutICSCFIncomingSIPTransactionsFailures       Unsigned32
}

sproutICSCFIncomingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutICSCFIncomingSIPTransactionsEntry 1 }

sproutICSCFIncomingSIPTransactionsRequestScope OBJECT-TYPE
    SYNTAX      RequestType
    MAX-ACCESS  not-accessible
    STATUS      current
    DESCRIPTION "The method type of the incoming transaction."
    ::= { sproutICSCFIncomingSIPTransactionsEntry 2 }

sproutICSCFIncomingSIPTransactionsAttempts OBJECT-TYPE
    SYNTAX      Unsigned32
    MAX-ACCESS  read-only
    STATUS      current
    DESCRIPTION "The number of incoming SIP transactions over the time period."
    ::= { sproutICSCFIncomingSIPTransactionsEntry 3 }

sproutICSCFIncomingSIPTransactionsSuccesses OBJECT-TYPE
    SYNTAX      Unsigned32
    MAX-ACCESS  read-only
    STATUS      current
    DESCRIPTION "The number of successful incoming SIP transactions over the
                 time period."
    ::= { sproutICSCFIncomingSIPTransactionsEntry 4 }

sproutICSCFIncomingSIPTransactionsFailures OBJECT-TYPE
    SYNTAX      Unsigned32
    MAX-ACCESS  read-only
    STATUS      current
    DESCRIPTION "The number of failed incoming SIP transactions over the
                 time period."
    ::= { sproutICSCFIncomingSIPTransactionsEntry 5 }

sproutICSCFOutgoingSIPTransactionsTable OBJECT-TYPE
    SYNTAX SEQUENCE OF SproutICSCFOutgoingSIPTransactionsEntry
    MAX-ACCESS not-accessible
    STATUS current
    DESCRIPTION "Counts the number of attempts, successes and failures
                 of outgoing SIP transactions for the ICSCF"
    ::= { sprout 19 }

sproutICSCFOutgoingSIPTransactionsEntry OBJECT-TYPE
    SYNTAX      SproutICSCFOutgoingSIPTransactionsEntry
    MAX-ACCESS  not-accessible
    STATUS      current
    DESCRIPTION "The number of attempts, successes and failures for
                 outgoing SIP transactions for the ICSCF"
    INDEX       { sproutICSCFOutgoingSIPTransactionsTimeScope,
                  sproutICSCFOutgoingSIPTransactionsRequestScope }
    ::= { sproutICSCFOutgoingSIPTransactionsTable 1 }

SproutICSCFOutgoingSIPTransactionsEntry ::= SEQUENCE
{
  sproutICSCFOutgoingSIPTransactionsTimeScope      INTEGER,
  sproutICSCFOutgoingSIPTransactionsRequestScope   INTEGER,
  sproutICSCFOutgoingSIPTransactionsAttempts       Unsigned32,
  sproutICSCFOutgoingSIPTransactionsSuccesses      Unsigned32,
  sproutICSCFOutgoingSIPTransactionsFailures       Unsigned32
}

sproutICSCFOutgoingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutICSCFOutgoingSIPTransactionsEntry 1 }

sproutICSCFOutgoingSIPTransactionsRequestScope OBJECT-TYPE
    SYNTAX      RequestType
    MAX-ACCESS  not-accessible
    STATUS      current
    DESCRIPTION "The method type of the outgoing transaction."
    ::= { sproutICSCFOutgoingSIPTransactionsEntry 2 }

sproutICSCFOutgoingSIPTransactionsAttempts OBJECT-TYPE
    SYNTAX      Unsigned32
    MAX-ACCESS  read-only
    STATUS      current
    DESCRIPTION "The number of outgoing SIP transactions over the time period."
    ::= { sproutICSCFOutgoingSIPTransactionsEntry 3 }

sproutICSCFOutgoingSIPTransactionsSuccesses OBJECT-TYPE
    SYNTAX      Unsigned32
    MAX-ACCESS  read-only
    STATUS      current
    DESCRIPTION "The number of successful outgoing SIP transactions over the
                 time period."
    ::= { sproutICSCFOutgoingSIPTransactionsEntry 4 }

sproutICSCFOutgoingSIPTransactionsFailures OBJECT-TYPE
    SYNTAX      Unsigned32
    MAX-ACCESS  read-only
    STATUS      current
    DESCRIPTION "The number of failed outgoing SIP transactions over the
                 time period."
    ::= { sproutICSCFOutgoingSIPTransactionsEntry 5 }

sproutSCSCFIncomingSIPTransactionsTable OBJECT-TYPE
    SYNTAX SEQUENCE OF SproutSCSCFIncomingSIPTransactionsEntry
    MAX-ACCESS not-accessible
    STATUS current
    DESCRIPTION "Counts the number of attempts, successes and failures
                 of incoming SIP transactions for the SCSCF"
    ::= { sprout 20 }

sproutSCSCFIncomingSIPTransactionsEntry OBJECT-TYPE
    SYNTAX      SproutSCSCFIncomingSIPTransactionsEntry
    MAX-ACCESS  not-accessible
    STATUS      current
    DESCRIPTION "The number of attempts, successes and failures for
                 incoming SIP transactions for the SCSCF"
    INDEX       { sproutSCSCFIncomingSIPTransactionsTimeScope,
                  sproutSCSCFIncomingSIPTransactionsRequestScope }
    ::= { sproutSCSCFIncomingSIPTransactionsTable 1 }

SproutSCSCFIncomingSIPTransactionsEntry ::= SEQUENCE
{
  sproutSCSCFIncomingSIPTransactionsTimeScope      INTEGER,
  sproutSCSCFIncomingSIPTransactionsRequestScope   INTEGER,
  sproutSCSCFIncomingSIPTransactionsAttempts       Unsigned32,
  sproutSCSCFIncomingSIPTransactionsSuccesses      Unsigned32,
  sproutSCSCFIncomingSIPTransactionsFailures       Unsigned32
}

sproutSCSCFIncomingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFIncomingSIPTransactionsEntry 1 }

sproutSCSCFIncomingSIPTransactionsRequestScope OBJECT-TYPE
    SYNTAX      RequestType
    MAX-ACCESS  not-accessible
    STATUS      current
    DESCRIPTION "The method type of the incoming transaction."
    ::= { sproutSCSCFIncomingSIPTransactionsEntry 2 }

sproutSCSCFIncomingSIPTransactionsAttempts OBJECT-TYPE
    SYNTAX      Unsigned32
    MAX-ACCESS  read-only
    STATUS      current
    DESCRIPTION "The number of incoming SIP transactions over the time period."
    ::= { sproutSCSCFIncomingSIPTransactionsEntry 3 }

sproutSCSCFIncomingSIPTransactionsSuccesses OBJECT-TYPE
    SYNTAX      Unsigned32
    MAX-ACCESS  read-only
    STATUS      current
    DESCRIPTION "The number of successful incoming SIP transactions over the
                 time period."
    ::= { sproutSCSCFIncomingSIPTransactionsEntry 4 }

sproutSCSCFIncomingSIPTransactionsFailures OBJECT-TYPE
    SYNTAX      Unsigned32
    MAX-ACCESS  read-only
    STATUS      current
    DESCRIPTION "The number of failed incoming SIP transactions over the
                 time period."
    ::= { sproutSCSCFIncomingSIPTransactionsEntry 5 }

sproutSCSCFOutgoingSIPTransactionsTable OBJECT-TYPE
    SYNTAX SEQUENCE OF SproutSCSCFOutgoingSIPTransactionsEntry
    MAX-ACCESS not-accessible
    STATUS current
    DESCRIPTION "Counts the number of attempts, successes and failures
                 of outgoing SIP transactions for the SCSCF"
    ::= { sprout 21 }

sproutSCSCFOutgoingSIPTransactionsEntry OBJECT-TYPE
    SYNTAX      SproutSCSCFOutgoingSIPTransactionsEntry
    MAX-ACCESS  not-accessible
    STATUS      current
    DESCRIPTION "The number of attempts, successes and failures for
                 outgoing SIP transactions for the SCSCF"
    INDEX       { sproutSCSCFOutgoingSIPTransactionsTimeScope,
                  sproutSCSCFOutgoingSIPTransactionsRequestScope }
    ::= { sproutSCSCFOutgoingSIPTransactionsTable 1 }

SproutSCSCFOutgoingSIPTransactionsEntry ::= SEQUENCE
{
  sproutSCSCFOutgoingSIPTransactionsTimeScope      INTEGER,
  sproutSCSCFOutgoingSIPTransactionsRequestScope   INTEGER,
  sproutSCSCFOutgoingSIPTransactionsAttempts       Unsigned32,
  sproutSCSCFOutgoingSIPTransactionsSuccesses      Unsigned32,
  sproutSCSCFOutgoingSIPTransactionsFailures       Unsigned32
}

sproutSCSCFOutgoingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFOutgoingSIPTransactionsEntry 1 }

sproutSCSCFOutgoingSIPTransactionsRequestScope OBJECT-TYPE
    SYNTAX      RequestType
    MAX-ACCESS  not-accessible
    STATUS      current
    DESCRIPTION "The method type of the outgoing transaction."
    ::= { sproutSCSCFOutgoingSIPTransactionsEntry 2 }

sproutSCSCFOutgoingSIPTransactionsAttempts OBJECT-TYPE
    SYNTAX      Unsigned32
    MAX-ACCESS  read-only
    STATUS      current
    DESCRIPTION "The number of outgoing SIP transactions over the time period."
    ::= { sproutSCSCFOutgoingSIPTransactionsEntry 3 }

sproutSCSCFOutgoingSIPTransactionsSuccesses OBJECT-TYPE
    SYNTAX      Unsigned32
    MAX-ACCESS  read-only
    STATUS      current
    DESCRIPTION "The number of successful outgoing SIP transactions over the
                 time period."
    ::= { sproutSCSCFOutgoingSIPTransactionsEntry 4 }

sproutSCSCFOutgoingSIPTransactionsFailures OBJECT-TYPE
    SYNTAX      Unsigned32
    MAX-ACCESS  read-only
    STATUS      current
    DESCRIPTION "The number of failed outgoing SIP transactions over the
                 time period."
    ::= { sproutSCSCFOutgoingSIPTransactionsEntry 5 }

sproutBGCFIncomingSIPTransactionsTable OBJECT-TYPE
    SYNTAX SEQUENCE OF SproutBGCFIncomingSIPTransactionsEntry
    MAX-ACCESS not-accessible
    STATUS current
    DESCRIPTION "Counts the number of attempts, successes and failures
                 of incoming SIP transactions for the BGCF"
    ::= { sprout 22 }

sproutBGCFIncomingSIPTransactionsEntry OBJECT-TYPE
    SYNTAX      SproutBGCFIncomingSIPTransactionsEntry
    MAX-ACCESS  not-accessible
    STATUS      current
    DESCRIPTION "The number of attempts, successes and failures for
                 incoming SIP transactions for the BGCF"
    INDEX       { sproutBGCFIncomingSIPTransactionsTimeScope,
                  sproutBGCFIncomingSIPTransactionsRequestScope }
    ::= { sproutBGCFIncomingSIPTransactionsTable 1 }

SproutBGCFIncomingSIPTransactionsEntry ::= SEQUENCE
{
  sproutBGCFIncomingSIPTransactionsTimeScope      INTEGER,
  sproutBGCFIncomingSIPTransactionsRequestScope   INTEGER,
  sproutBGCFIncomingSIPTransactionsAttempts       Unsigned32,
  sproutBGCFIncomingSIPTransactionsSuccesses      Unsigned32,
  sproutBGCFIncomingSIPTransactionsFailures       Unsigned32
}

sproutBGCFIncomingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutBGCFIncomingSIPTransactionsEntry 1 }

sproutBGCFIncomingSIPTransactionsRequestScope OBJECT-TYPE
    SYNTAX      RequestType
    MAX-ACCESS  not-accessible
    STATUS      current
    DESCRIPTION "The method type of the incoming transaction."
    ::= { sproutBGCFIncomingSIPTransactionsEntry 2 }

sproutBGCFIncomingSIPTransactionsAttempts OBJECT-TYPE
    SYNTAX      Unsigned32
    MAX-ACCESS  read-only
    STATUS      current
    DESCRIPTION "The number of incoming SIP transactions over the time period."
    ::= { sproutBGCFIncomingSIPTransactionsEntry 3 }

sproutBGCFIncomingSIPTransactionsSuccesses OBJECT-TYPE
    SYNTAX      Unsigned32
    MAX-ACCESS  read-only
    STATUS      current
    DESCRIPTION "The number of successful incoming SIP transactions over the
                 time period."
    ::= { sproutBGCFIncomingSIPTransactionsEntry 4 }

sproutBGCFIncomingSIPTransactionsFailures OBJECT-TYPE
    SYNTAX      Unsigned32
    MAX-ACCESS  read-only
    STATUS      current
    DESCRIPTION "The number of failed incoming SIP transactions over the
                 time period."
    ::= { sproutBGCFIncomingSIPTransactionsEntry 5 }

sproutBGCFOutgoingSIPTransactionsTable OBJECT-TYPE
    SYNTAX SEQUENCE OF SproutBGCFOutgoingSIPTransactionsEntry
    MAX-ACCESS not-accessible
    STATUS current
    DESCRIPTION "Counts the number of attempts, successes and failures
                 of outgoing SIP transactions for the BGCF"
    ::= { sprout 23 }

sproutBGCFOutgoingSIPTransactionsEntry OBJECT-TYPE
    SYNTAX      SproutBGCFOutgoingSIPTransactionsEntry
    MAX-ACCESS  not-accessible
    STATUS      current
    DESCRIPTION "The number of attempts, successes and failures for
                 outgoing SIP transactions for the BGCF"
    INDEX       { sproutBGCFOutgoingSIPTransactionsTimeScope,
                  sproutBGCFOutgoingSIPTransactionsRequestScope }
    ::= { sproutBGCFOutgoingSIPTransactionsTable 1 }

SproutBGCFOutgoingSIPTransactionsEntry ::= SEQUENCE
{
  sproutBGCFOutgoingSIPTransactionsTimeScope      INTEGER,
  sproutBGCFOutgoingSIPTransactionsRequestScope   INTEGER,
  sproutBGCFOutgoingSIPTransactionsAttempts       Unsigned32,
  sproutBGCFOutgoingSIPTransactionsSuccesses      Unsigned32,
  sproutBGCFOutgoingSIPTransactionsFailures       Unsigned32
}

sproutBGCFOutgoingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutBGCFOutgoingSIPTransactionsEntry 1 }

sproutBGCFOutgoingSIPTransactionsRequestScope OBJECT-TYPE
    SYNTAX      RequestType
    MAX-ACCESS  not-accessible
    STATUS      current
    DESCRIPTION "The method type of the outgoing transaction."
    ::= { sproutBGCFOutgoingSIPTransactionsEntry 2 }

sproutBGCFOutgoingSIPTransactionsAttempts OBJECT-TYPE
    SYNTAX      Unsigned32
    MAX-ACCESS  read-only
    STATUS      current
    DESCRIPTION "The number of outgoing SIP transactions over the time period."
    ::= { sproutBGCFOutgoingSIPTransactionsEntry 3 }

sproutBGCFOutgoingSIPTransactionsSuccesses OBJECT-TYPE
    SYNTAX      Unsigned32
    MAX-ACCESS  read-only
    STATUS      current
    DESCRIPTION "The number of successful outgoing SIP transactions over the
                 time period."
    ::= { sproutBGCFOutgoingSIPTransactionsEntry 4 }

sproutBGCFOutgoingSIPTransactionsFailures OBJECT-TYPE
    SYNTAX      Unsigned32
    MAX-ACCESS  read-only
    STATUS      current
    DESCRIPTION "The number of failed outgoing SIP transactions over the
                 time period."
    ::= { sproutBGCFOutgoingSIPTransactionsEntry 5 }

sproutMMTelIncomingSIPTransactionsTable OBJECT-TYPE
    SYNTAX SEQUENCE OF SproutMMTelIncomingSIPTransactionsEntry
    MAX-ACCESS not-accessible
    STATUS current
    DESCRIPTION "Counts the number of attempts, successes and failures
                 of incoming SIP transactions for the MMTel"
    ::= { sprout 24 }

sproutMMTelIncomingSIPTransactionsEntry OBJECT-TYPE
    SYNTAX      SproutMMTelIncomingSIPTransactionsEntry
    MAX-ACCESS  not-accessible
    STATUS      current
    DESCRIPTION "The number of attempts, successes and failures for
                 incoming SIP transactions for the MMTel"
    INDEX       { sproutMMTelIncomingSIPTransactionsTimeScope,
                  sproutMMTelIncomingSIPTransactionsRequestScope }
    ::= { sproutMMTelIncomingSIPTransactionsTable 1 }

SproutMMTelIncomingSIPTransactionsEntry ::= SEQUENCE
{
  sproutMMTelIncomingSIPTransactionsTimeScope      INTEGER,
  sproutMMTelIncomingSIPTransactionsRequestScope   INTEGER,
  sproutMMTelIncomingSIPTransactionsAttempts       Unsigned32,
  sproutMMTelIncomingSIPTransactionsSuccesses      Unsigned32,
  sproutMMTelIncomingSIPTransactionsFailures       Unsigned32
}

sproutMMTelIncomingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutMMTelIncomingSIPTransactionsEntry 1 }

sproutMMTelIncomingSIPTransactionsRequestScope OBJECT-TYPE
    SYNTAX      RequestType
    MAX-ACCESS  not-accessible
    STATUS      current
    DESCRIPTION "The method type of the incoming transaction."
    ::= { sproutMMTelIncomingSIPTransactionsEntry 2 }

sproutMMTelIncomingSIPTransactionsAttempts OBJECT-TYPE
    SYNTAX      Unsigned32
    MAX-ACCESS  read-only
    STATUS      current
    DESCRIPTION "The number of incoming SIP transactions over the time period."
    ::= { sproutMMTelIncomingSIPTransactionsEntry 3 }

sproutMMTelIncomingSIPTransactionsSuccesses OBJECT-TYPE
    SYNTAX      Unsigned32
    MAX-ACCESS  read-only
    STATUS      current
    DESCRIPTION "The number of successful incoming SIP transactions over the
                 time period."
    ::= { sproutMMTelIncomingSIPTransactionsEntry 4 }

sproutMMTelIncomingSIPTransactionsFailures OBJECT-TYPE
    SYNTAX      Unsigned32
    MAX-ACCESS  read-only
    STATUS      current
    DESCRIPTION "The number of failed incoming SIP transactions over the
                 time period."
    ::= { sproutMMTelIncomingSIPTransactionsEntry 5 }

sproutMMTelOutgoingSIPTransactionsTable OBJECT-TYPE
    SYNTAX SEQUENCE OF SproutMMTelOutgoingSIPTransactionsEntry
    MAX-ACCESS not-accessible
    STATUS current
    DESCRIPTION "Counts the number of attempts, successes and failures
                 of outgoing SIP transactions for the MMTel"
    ::= { sprout 25 }

sproutMMTelOutgoingSIPTransactionsEntry OBJECT-TYPE
    SYNTAX      SproutMMTelOutgoingSIPTransactionsEntry
    MAX-ACCESS  not-accessible
    STATUS      current
    DESCRIPTION "The number of attempts, successes and failures for
                 outgoing SIP transactions for the MMTel"
    INDEX       { sproutMMTelOutgoingSIPTransactionsTimeScope,
                  sproutMMTelOutgoingSIPTransactionsRequestScope }
    ::= { sproutMMTelOutgoingSIPTransactionsTable 1 }

SproutMMTelOutgoingSIPTransactionsEntry ::= SEQUENCE
{
  sproutMMTelOutgoingSIPTransactionsTimeScope      INTEGER,
  sproutMMTelOutgoingSIPTransactionsRequestScope   INTEGER,
  sproutMMTelOutgoingSIPTransactionsAttempts       Unsigned32,
  sproutMMTelOutgoingSIPTransactionsSuccesses      Unsigned32,
  sproutMMTelOutgoingSIPTransactionsFailures       Unsigned32
}

sproutMMTelOutgoingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutMMTelOutgoingSIPTransactionsEntry 1 }

sproutMMTelOutgoingSIPTransactionsRequestScope OBJECT-TYPE
    SYNTAX      RequestType
    MAX-ACCESS  not-accessible
    STATUS      current
    DESCRIPTION "The method type of the outgoing transaction."
    ::= { sproutMMTelOutgoingSIPTransactionsEntry 2 }

sproutMMTelOutgoingSIPTransactionsAttempts OBJECT-TYPE
    SYNTAX      Unsigned32
    MAX-ACCESS  read-only
    STATUS      current
    DESCRIPTION "The number of outgoing SIP transactions over the time period."
    ::= { sproutMMTelOutgoingSIPTransactionsEntry 3 }

sproutMMTelOutgoingSIPTransactionsSuccesses OBJECT-TYPE
    SYNTAX      Unsigned32
    MAX-ACCESS  read-only
    STATUS      current
    DESCRIPTION "The number of successful outgoing SIP transactions over the
                 time period."
    ::= { sproutMMTelOutgoingSIPTransactionsEntry 4 }

sproutMMTelOutgoingSIPTransactionsFailures OBJECT-TYPE
    SYNTAX      Unsigned32
    MAX-ACCESS  read-only
    STATUS      current
    DESCRIPTION "The number of failed outgoing SIP transactions over the
                 time period."
    ::= { sproutMMTelOutgoingSIPTransactionsEntry 5 }

sproutRequestsRoutedByPreloadedRouteTable OBJECT-TYPE
    SYNTAX SEQUENCE OF SproutRequestsRoutedByPreloadedRouteEntry
    MAX-ACCESS not-accessible
    STATUS current
    DESCRIPTION "Number of requests routed according to a pre-loaded route by
                 the SCSCF over the given time period."
    ::= { sprout 26 }

sproutRequestsRoutedByPreloadedRouteEntry OBJECT-TYPE
    SYNTAX      SproutRequestsRoutedByPreloadedRouteEntry
    MAX-ACCESS  not-accessible
    STATUS      current
    DESCRIPTION "The number of requests routed according to a pre-loaded route
                 by the SCSCF."
    INDEX       { sproutRequestsRoutedByPreloadedRouteScope }
    ::= { sproutRequestsRoutedByPreloadedRouteTable 1 }

SproutRequestsRoutedByPreloadedRouteEntry ::= SEQUENCE
{
  sproutRequestsRoutedByPreloadedRouteScope        INTEGER,
  sproutRequestsRoutedByPreloadedRouteCount        Unsigned32
}

sproutRequestsRoutedByPreloadedRouteScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutRequestsRoutedByPreloadedRouteEntry 1 }

sproutRequestsRoutedByPreloadedRouteCount OBJECT-TYPE
    SYNTAX      Unsigned32
    MAX-ACCESS  read-only
    STATUS      current
    DESCRIPTION "The number of requests routed according to a pre-loaded route
                 over the given time period."
    ::= { sproutRequestsRoutedByPreloadedRouteEntry 2 }


sproutPRRTable OBJECT-TYPE
    SYNTAX SEQUENCE OF SproutPRREntry
    MAX-ACCESS not-accessible
    STATUS     current
    DESCRIPTION "Statistics for the value of the permitted request rate.
                 The permitted request rate (PRR) is an estimate for the
                 sustainable request rate without causing large latency."
    ::= { sprout 27 }

sproutPRREntry OBJECT-TYPE
    SYNTAX      SproutPRREntry
    MAX-ACCESS  not-accessible
    STATUS      current
    DESCRIPTION "The average, variance, HWM, LWM and count of the permitted request rate"
    INDEX       { sproutPRRScope }
    ::= { sproutPRRTable 1 }

SproutPRREntry ::= SEQUENCE
{
  sproutPRRScope          INTEGER,
  sproutPRRAverage        Unsigned32,
  sproutPRRVariance       Unsigned32,
  sproutPRRHWM            Unsigned32,
  sproutPRRLWM            Unsigned32,
  sproutPRRCount          Unsigned32
}

sproutPRRScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutPRREntry 1 }

sproutPRRAverage OBJECT-TYPE
    SYNTAX      Unsigned32
    MAX-ACCESS  read-only
    STATUS      current
    DESCRIPTION "The average permitted request rate over the period."
    ::= { sproutPRREntry 2 }

sproutPRRVariance OBJECT-TYPE
    SYNTAX      Unsigned32
    MAX-ACCESS  read-only
    STATUS      current
    DESCRIPTION "The variance of the permitted request rate over the period."
    ::= { sproutPRREntry 3 }

sproutPRRHWM OBJECT-TYPE
    SYNTAX      Unsigned32
    MAX-ACCESS  read-only
    STATUS      current
    DESCRIPTION "The highest permitted request rate over the period."
    ::= { sproutPRREntry 4 }

sproutPRRLWM OBJECT-TYPE
    SYNTAX      Unsigned32
    MAX-ACCESS  read-only
    STATUS      current
    DESCRIPTION "The lowest permitted request rate over the period."
    ::= { sproutPRREntry 5 }

sproutPRRCount OBJECT-TYPE
    SYNTAX      Unsigned32
    MAX-ACCESS  read-only
    STATUS      current
    DESCRIPTION "The total number of permitted request rate
                 updates over the period."
    ::= { sproutPRREntry 6 }

sproutSmoothedLatencyValue OBJECT-TYPE
    SYNTAX      Unsigned32
    MAX-ACCESS  read-only
    STATUS      current
    DESCRIPTION "The smoothed latency value at last PRR update.
                 The permitted request rate (PRR) is an estimate for the
                 sustainable request rate without causing large latency."
    ::= { sprout 28 }

sproutTargetLatencyValue OBJECT-TYPE
    SYNTAX      Unsigned32
    MAX-ACCESS  read-only
    STATUS      current
    DESCRIPTION "The maximum acceptable latency that
                 should be experienced by requests."
    ::= { sprout 29 }

sproutPenaltiesValue OBJECT-TYPE
    SYNTAX      Unsigned32
    MAX-ACCESS  read-only
    STATUS      current
    DESCRIPTION "The number of overload responses
                 Sprout received from upstream at last PRR update.
                 The permitted request rate (PRR) is an estimate for the
                 sustainable request rate without causing large latency."
    ::= { sprout 30 }

sproutPRRCurrentValue OBJECT-TYPE
    SYNTAX      Unsigned32
    MAX-ACCESS  read-only
    STATUS      current
    DESCRIPTION "The curent permitted request rate.
                 The permitted request rate (PRR) is an estimate for the
                 sustainable request rate without causing large latency."
    ::= { sprout 31 }

sproutGroup OBJECT-GROUP
    OBJECTS {
      sproutLatencyAverage,
      sproutLatencyVariance,
      sproutLatencyHWM,
      sproutLatencyLWM,
      sproutLatencyCount,
      sproutHomerConnectionCount,
      sproutHomerLatencyAverage,
      sproutHomerLatencyVariance,
      sproutHomerLatencyHWM,
      sproutHomerLatencyLWM,
      sproutHomerLatencyCount,
      sproutHomesteadConnectionCount,
      sproutHomesteadLatencyAverage,
      sproutHomesteadLatencyVariance,
      sproutHomesteadLatencyHWM,
      sproutHomesteadLatencyLWM,
      sproutHomesteadLatencyCount,
      sproutMARLatencyAverage,
      sproutMARLatencyVariance,
      sproutMARLatencyHWM,
      sproutMARLatencyLWM,
      sproutMARLatencyCount,
      sproutSARLatencyAverage,
      sproutSARLatencyVariance,
      sproutSARLatencyHWM,
      sproutSARLatencyLWM,
      sproutSARLatencyCount,
      sproutUARLatencyAverage,
      sproutUARLatencyVariance,
      sproutUARLatencyHWM,
      sproutUARLatencyLWM,
      sproutUARLatencyCount,
      sproutLIRLatencyAverage,
      sproutLIRLatencyVariance,
      sproutLIRLatencyHWM,
      sproutLIRLatencyLWM,
      sproutLIRLatencyCount,
      sproutIncomingRequestsCount,
      sproutRejectedOverloadCount,
      sproutQueueSizeAverage,
      sproutQueueSizeVariance,
      sproutQueueSizeHWM,
      sproutQueueSizeLWM,
      sproutQueueSizeCount,
      sproutInitialRegistrationAttempts,
      sproutInitialRegistrationSuccesses,
      sproutInitialRegistrationFailures,
      sproutReRegistrationAttempts,
      sproutReRegistrationSuccesses,
      sproutReRegistrationFailures,
      sproutDeRegistrationAttempts,
      sproutDeRegistrationSuccesses,
      sproutDeRegistrationFailures,
      sproutThirdPartyInitialRegistrationAttempts,
      sproutThirdPartyInitialRegistrationSuccesses,
      sproutThirdPartyInitialRegistrationFailures,
      sproutThirdPartyReRegistrationAttempts,
      sproutThirdPartyReRegistrationSuccesses,
      sproutThirdPartyReRegistrationFailures,
      sproutThirdPartyDeRegistrationAttempts,
      sproutThirdPartyDeRegistrationSuccesses,
      sproutThirdPartyDeRegistrationFailures,
      sproutSIPDigestAuthenticationAttempts,
      sproutSIPDigestAuthenticationSuccesses,
      sproutSIPDigestAuthenticationFailures,
      sproutAKAAuthenticationAttempts,
      sproutAKAAuthenticationSuccesses,
      sproutAKAAuthenticationFailures,
      sproutNonRegisterAuthenticationAttempts,
      sproutNonRegisterAuthenticationSuccesses,
      sproutNonRegisterAuthenticationFailures,
      sproutICSCFIncomingSIPTransactionsAttempts,
      sproutICSCFIncomingSIPTransactionsSuccesses,
      sproutICSCFIncomingSIPTransactionsFailures,
      sproutICSCFOutgoingSIPTransactionsAttempts,
      sproutICSCFOutgoingSIPTransactionsSuccesses,
      sproutICSCFOutgoingSIPTransactionsFailures,
      sproutSCSCFIncomingSIPTransactionsAttempts,
      sproutSCSCFIncomingSIPTransactionsSuccesses,
      sproutSCSCFIncomingSIPTransactionsFailures,
      sproutSCSCFOutgoingSIPTransactionsAttempts,
      sproutSCSCFOutgoingSIPTransactionsSuccesses,
      sproutSCSCFOutgoingSIPTransactionsFailures,
      sproutBGCFIncomingSIPTransactionsAttempts,
      sproutBGCFIncomingSIPTransactionsSuccesses,
      sproutBGCFIncomingSIPTransactionsFailures,
      sproutBGCFOutgoingSIPTransactionsAttempts,
      sproutBGCFOutgoingSIPTransactionsSuccesses,
      sproutBGCFOutgoingSIPTransactionsFailures,
      sproutMMTelIncomingSIPTransactionsAttempts,
      sproutMMTelIncomingSIPTransactionsSuccesses,
      sproutMMTelIncomingSIPTransactionsFailures,
      sproutMMTelOutgoingSIPTransactionsAttempts,
      sproutMMTelOutgoingSIPTransactionsSuccesses,
      sproutMMTelOutgoingSIPTransactionsFailures,
      sproutRequestsRoutedByPreloadedRouteCount,
      sproutPRRAverage,
      sproutPRRVariance,
      sproutPRRHWM,
      sproutPRRLWM,
      sproutPRRCount,
      sproutSmoothedLatencyValue,
      sproutTargetLatencyValue,
      sproutPenaltiesValue,
      sproutPRRCurrentValue
    }
    STATUS      current
    DESCRIPTION "Statistics exposed by Sprout"
    ::= { projectClearwaterObjectGroups 2 }

-- Homestead entries

homesteadLatencyTable OBJECT-TYPE
    SYNTAX SEQUENCE OF HomesteadLatencyEntry
    MAX-ACCESS not-accessible
    STATUS current
    DESCRIPTION "Latency of HTTP requests handled by this Homestead
                 over the given period.  Latency measured in
                 microseconds"
    ::= { homestead 1 }

homesteadLatencyEntry OBJECT-TYPE
    SYNTAX      HomesteadLatencyEntry
    MAX-ACCESS  not-accessible
    STATUS      current
    DESCRIPTION "The average, variance, LWM and HWM of HTTP request
                 latency"
    INDEX       { homesteadLatencyScope }
    ::= { homesteadLatencyTable 1 }

HomesteadLatencyEntry ::= SEQUENCE
{
  homesteadLatencyScope          INTEGER,
  homesteadLatencyAverage        Unsigned32,
  homesteadLatencyVariance       Unsigned32,
  homesteadLatencyHWM            Unsigned32,
  homesteadLatencyLWM            Unsigned32,
  homesteadLatencyCount          Unsigned32
}

homesteadLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadLatencyEntry 1 }

homesteadLatencyAverage OBJECT-TYPE
    SYNTAX      Unsigned32
    MAX-ACCESS  read-only
    STATUS      current
    DESCRIPTION "The average latency over the period."
    ::= { homesteadLatencyEntry 2 }

homesteadLatencyVariance OBJECT-TYPE
    SYNTAX      Unsigned32
    MAX-ACCESS  read-only
    STATUS      current
    DESCRIPTION "The variance of the latency over the period."
    ::= { homesteadLatencyEntry 3 }

homesteadLatencyHWM OBJECT-TYPE
    SYNTAX      Unsigned32
    MAX-ACCESS  read-only
    STATUS      current
    DESCRIPTION "The highest latency over the period."
    ::= { homesteadLatencyEntry 4 }

homesteadLatencyLWM OBJECT-TYPE
    SYNTAX      Unsigned32
    MAX-ACCESS  read-only
    STATUS      current
    DESCRIPTION "The lowest latency over the period."
    ::= { homesteadLatencyEntry 5 }

homesteadLatencyCount OBJECT-TYPE
    SYNTAX      Unsigned32
    MAX-ACCESS  read-only
    STATUS      current
    DESCRIPTION "The total requests over the period."
    ::= { homesteadLatencyEntry 6 }

homesteadHSSLatencyTable OBJECT-TYPE
    SYNTAX SEQUENCE OF HomesteadHSSLatencyEntry
    MAX-ACCESS not-accessible
    STATUS current
    DESCRIPTION "Latency of HSS requests made by this Homestead
                 over the given period.  Latency measured in
                 microseconds"
    ::= { homestead 2 }

homesteadHSSLatencyEntry OBJECT-TYPE
    SYNTAX      HomesteadHSSLatencyEntry
    MAX-ACCESS  not-accessible
    STATUS      current
    DESCRIPTION "The average, variance, LWM and HWM of HSS request
                 latency"
    INDEX       { homesteadHSSLatencyScope }
    ::= { homesteadHSSLatencyTable 1 }

HomesteadHSSLatencyEntry ::= SEQUENCE
{
  homesteadHSSLatencyScope          INTEGER,
  homesteadHSSLatencyAverage        Unsigned32,
  homesteadHSSLatencyVariance       Unsigned32,
  homesteadHSSLatencyHWM            Unsigned32,
  homesteadHSSLatencyLWM            Unsigned32,
  homesteadHSSLatencyCount          Unsigned32
}

homesteadHSSLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadHSSLatencyEntry 1 }

homesteadHSSLatencyAverage OBJECT-TYPE
    SYNTAX      Unsigned32
    MAX-ACCESS  read-only
    STATUS      current
    DESCRIPTION "The average latency over the period."
    ::= { homesteadHSSLatencyEntry 2 }

homesteadHSSLatencyVariance OBJECT-TYPE
    SYNTAX      Unsigned32
    MAX-ACCESS  read-only
    STATUS      current
    DESCRIPTION "The variance of the latency over the period."
    ::= { homesteadHSSLatencyEntry 3 }

homesteadHSSLatencyHWM OBJECT-TYPE
    SYNTAX      Unsigned32
    MAX-ACCESS  read-only
    STATUS      current
    DESCRIPTION "The highest latency over the period."
    ::= { homesteadHSSLatencyEntry 4 }

homesteadHSSLatencyLWM OBJECT-TYPE
    SYNTAX      Unsigned32
    MAX-ACCESS  read-only
    STATUS      current
    DESCRIPTION "The lowest latency over the period."
    ::= { homesteadHSSLatencyEntry 5 }

homesteadHSSLatencyCount OBJECT-TYPE
    SYNTAX      Unsigned32
    MAX-ACCESS  read-only
    STATUS      current
    DESCRIPTION "The total requests over the period."
    ::= { homesteadHSSLatencyEntry 6 }

homesteadCacheLatencyTable OBJECT-TYPE
    SYNTAX SEQUENCE OF HomesteadCacheLatencyEntry
    MAX-ACCESS not-accessible
    STATUS current
    DESCRIPTION "Latency of cache requests made by this Homestead
                 over a the given period.  Latency measured in
                 microseconds"
    ::= { homestead 3 }

homesteadCacheLatencyEntry OBJECT-TYPE
    SYNTAX      HomesteadCacheLatencyEntry
    MAX-ACCESS  not-accessible
    STATUS      current
    DESCRIPTION "The average, variance, LWM and HWM of request
                 latency"
    INDEX       { homesteadCacheLatencyScope }
    ::= { homesteadCacheLatencyTable 1 }

HomesteadCacheLatencyEntry ::= SEQUENCE
{
  homesteadCacheLatencyScope          INTEGER,
  homesteadCacheLatencyAverage        Unsigned32,
  homesteadCacheLatencyVariance       Unsigned32,
  homesteadCacheLatencyHWM            Unsigned32,
  homesteadCacheLatencyLWM            Unsigned32,
  homesteadCacheLatencyCount          Unsigned32
}

homesteadCacheLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadCacheLatencyEntry 1 }

homesteadCacheLatencyAverage OBJECT-TYPE
    SYNTAX      Unsigned32
    MAX-ACCESS  read-only
    STATUS      current
    DESCRIPTION "The average latency over the period."
    ::= { homesteadCacheLatencyEntry 2 }

homesteadCacheLatencyVariance OBJECT-TYPE
    SYNTAX      Unsigned32
    MAX-ACCESS  read-only
    STATUS      current
    DESCRIPTION "The variance of the latency over the period."
    ::= { homesteadCacheLatencyEntry 3 }

homesteadCacheLatencyHWM OBJECT-TYPE
    SYNTAX      Unsigned32
    MAX-ACCESS  read-only
    STATUS      current
    DESCRIPTION "The highest latency over the period."
    ::= { homesteadCacheLatencyEntry 4 }

homesteadCacheLatencyLWM OBJECT-TYPE
    SYNTAX      Unsigned32
    MAX-ACCESS  read-only
    STATUS      current
    DESCRIPTION "The lowest latency over the period."
    ::= { homesteadCacheLatencyEntry 5 }

homesteadCacheLatencyCount OBJECT-TYPE
    SYNTAX      Unsigned32
    MAX-ACCESS  read-only
    STATUS      current
    DESCRIPTION "The total requests over the period."
    ::= { homesteadCacheLatencyEntry 6 }

homesteadDigestLatencyTable OBJECT-TYPE
    SYNTAX SEQUENCE OF HomesteadDigestLatencyEntry
    MAX-ACCESS not-accessible
    STATUS current
    DESCRIPTION "Latency of requests for Digests made by this Homestead
                 over the given period.  Latency measured in
                 microseconds"
    ::= { homestead 4 }

homesteadDigestLatencyEntry OBJECT-TYPE
    SYNTAX      HomesteadDigestLatencyEntry
    MAX-ACCESS  not-accessible
    STATUS      current
    DESCRIPTION "The average, variance, LWM and HWM of request
                 latency"
    INDEX       { homesteadDigestLatencyScope }
    ::= { homesteadDigestLatencyTable 1 }

HomesteadDigestLatencyEntry ::= SEQUENCE
{
  homesteadDigestLatencyScope          INTEGER,
  homesteadDigestLatencyAverage        Unsigned32,
  homesteadDigestLatencyVariance       Unsigned32,
  homesteadDigestLatencyHWM            Unsigned32,
  homesteadDigestLatencyLWM            Unsigned32,
  homesteadDigestLatencyCount          Unsigned32
}

homesteadDigestLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadDigestLatencyEntry 1 }

homesteadDigestLatencyAverage OBJECT-TYPE
    SYNTAX      Unsigned32
    MAX-ACCESS  read-only
    STATUS      current
    DESCRIPTION "The average latency over the period."
    ::= { homesteadDigestLatencyEntry 2 }

homesteadDigestLatencyVariance OBJECT-TYPE
    SYNTAX      Unsigned32
    MAX-ACCESS  read-only
    STATUS      current
    DESCRIPTION "The variance of the latency over the period."
    ::= { homesteadDigestLatencyEntry 3 }

homesteadDigestLatencyHWM OBJECT-TYPE
    SYNTAX      Unsigned32
    MAX-ACCESS  read-only
    STATUS      current
    DESCRIPTION "The highest latency over the period."
    ::= { homesteadDigestLatencyEntry 4 }

homesteadDigestLatencyLWM OBJECT-TYPE
    SYNTAX      Unsigned32
    MAX-ACCESS  read-only
    STATUS      current
    DESCRIPTION "The lowest latency over the period."
    ::= { homesteadDigestLatencyEntry 5 }

homesteadDigestLatencyCount OBJECT-TYPE
    SYNTAX      Unsigned32
    MAX-ACCESS  read-only
    STATUS      current
    DESCRIPTION "The total requests over the period."
    ::= { homesteadDigestLatencyEntry 6 }

homesteadSubscriptionLatencyTable OBJECT-TYPE
    SYNTAX SEQUENCE OF HomesteadSubscriptionLatencyEntry
    MAX-ACCESS not-accessible
    STATUS current
    DESCRIPTION "Latency of requests for Subscriptions made by this Homestead
                 over the given period.  Latency measured in
                 microseconds"
    ::= { homestead 5 }

homesteadSubscriptionLatencyEntry OBJECT-TYPE
    SYNTAX      HomesteadSubscriptionLatencyEntry
    MAX-ACCESS  not-accessible
    STATUS      current
    DESCRIPTION "The average, variance, LWM and HWM of request
                 latency"
    INDEX       { homesteadSubscriptionLatencyScope }
    ::= { homesteadSubscriptionLatencyTable 1 }

HomesteadSubscriptionLatencyEntry ::= SEQUENCE
{
  homesteadSubscriptionLatencyScope          INTEGER,
  homesteadSubscriptionLatencyAverage        Unsigned32,
  homesteadSubscriptionLatencyVariance       Unsigned32,
  homesteadSubscriptionLatencyHWM            Unsigned32,
  homesteadSubscriptionLatencyLWM            Unsigned32,
  homesteadSubscriptionLatencyCount          Unsigned32
}

homesteadSubscriptionLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadSubscriptionLatencyEntry 1 }

homesteadSubscriptionLatencyAverage OBJECT-TYPE
    SYNTAX      Unsigned32
    MAX-ACCESS  read-only
    STATUS      current
    DESCRIPTION "The average latency over the period."
    ::= { homesteadSubscriptionLatencyEntry 2 }

homesteadSubscriptionLatencyVariance OBJECT-TYPE
    SYNTAX      Unsigned32
    MAX-ACCESS  read-only
    STATUS      current
    DESCRIPTION "The variance of the latency over the period."
    ::= { homesteadSubscriptionLatencyEntry 3 }

homesteadSubscriptionLatencyHWM OBJECT-TYPE
    SYNTAX      Unsigned32
    MAX-ACCESS  read-only
    STATUS      current
    DESCRIPTION "The highest latency over the period."
    ::= { homesteadSubscriptionLatencyEntry 4 }

homesteadSubscriptionLatencyLWM OBJECT-TYPE
    SYNTAX      Unsigned32
    MAX-ACCESS  read-only
    STATUS      current
    DESCRIPTION "The lowest latency over the period."
    ::= { homesteadSubscriptionLatencyEntry 5 }

homesteadSubscriptionLatencyCount OBJECT-TYPE
    SYNTAX      Unsigned32
    MAX-ACCESS  read-only
    STATUS      current
    DESCRIPTION "The total requests over the period."
    ::= { homesteadSubscriptionLatencyEntry 6 }

homesteadIncomingRequestsTable OBJECT-TYPE
    SYNTAX SEQUENCE OF HomesteadIncomingRequestsEntry
    MAX-ACCESS not-accessible
    STATUS current
    DESCRIPTION "Total number of incoming requests handled by this Homestead
                 over the given period."
    ::= { homestead 6 }

homesteadIncomingRequestsEntry OBJECT-TYPE
    SYNTAX      HomesteadIncomingRequestsEntry
    MAX-ACCESS  not-accessible
    STATUS      current
    DESCRIPTION "The total number of incoming requests"
    INDEX       { homesteadIncomingRequestsScope }
    ::= { homesteadIncomingRequestsTable 1 }

HomesteadIncomingRequestsEntry ::= SEQUENCE
{
  homesteadIncomingRequestsScope          INTEGER,
  homesteadIncomingRequestsCount          Unsigned32
}

homesteadIncomingRequestsScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadIncomingRequestsEntry 1 }

homesteadIncomingRequestsCount OBJECT-TYPE
    SYNTAX      Unsigned32
    MAX-ACCESS  read-only
    STATUS      current
    DESCRIPTION "The total number of incoming requests over the period."
    ::= { homesteadIncomingRequestsEntry 2 }

homesteadRejectedOverloadTable OBJECT-TYPE
    SYNTAX SEQUENCE OF HomesteadRejectedOverloadEntry
    MAX-ACCESS not-accessible
    STATUS current
    DESCRIPTION "Total number of requests rejected due to overload by
                 this Homestead over the given period."
    ::= { homestead 7 }

homesteadRejectedOverloadEntry OBJECT-TYPE
    SYNTAX      HomesteadRejectedOverloadEntry
    MAX-ACCESS  not-accessible
    STATUS      current
    DESCRIPTION "The total number of requests rejected due to overload"
    INDEX       { homesteadRejectedOverloadScope }
    ::= { homesteadRejectedOverloadTable 1 }

HomesteadRejectedOverloadEntry ::= SEQUENCE
{
  homesteadRejectedOverloadScope          INTEGER,
  homesteadRejectedOverloadCount          Unsigned32
}

homesteadRejectedOverloadScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadRejectedOverloadEntry 1 }

homesteadRejectedOverloadCount OBJECT-TYPE
    SYNTAX      Unsigned32
    MAX-ACCESS  read-only
    STATUS      current
    DESCRIPTION "The total number of rejected requests due to overload over the
                 period."
    ::= { homesteadRejectedOverloadEntry 2 }

homesteadDiameterInvalidRealmTable OBJECT-TYPE
    SYNTAX SEQUENCE OF HomesteadDiameterInvalidRealmEntry
    MAX-ACCESS not-accessible
    STATUS current
    DESCRIPTION "The total number of Diameter requests with an invalid Destination-Realm handled by the Homestead
                 over the given period."
    ::= { homestead 8 }

homesteadDiameterInvalidRealmEntry OBJECT-TYPE
    SYNTAX      HomesteadDiameterInvalidRealmEntry
    MAX-ACCESS  not-accessible
    STATUS      current
    DESCRIPTION "The total number of Diameter requests with an invalid Destination-Realm."
    INDEX       { homesteadDiameterInvalidRealmScope }
    ::= { homesteadDiameterInvalidRealmTable 1 }

HomesteadDiameterInvalidRealmEntry ::= SEQUENCE
{
  homesteadDiameterInvalidRealmScope          INTEGER,
  homesteadDiameterInvalidRealmCount          Unsigned32
}

homesteadDiameterInvalidRealmScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadDiameterInvalidRealmEntry 1 }

homesteadDiameterInvalidRealmCount OBJECT-TYPE
    SYNTAX      Unsigned32
    MAX-ACCESS  read-only
    STATUS      current
    DESCRIPTION "The total number of Diameter requests with an invalid Destination-Realm over the period."
    ::= { homesteadDiameterInvalidRealmEntry 2 }

homesteadDiameterInvalidHostTable OBJECT-TYPE
    SYNTAX SEQUENCE OF HomesteadDiameterInvalidHostEntry
    MAX-ACCESS not-accessible
    STATUS current
    DESCRIPTION "The total number of Diameter requests with an invalid Destination-Host handled by the Homestead
                 over the given period."
    ::= { homestead 9 }

homesteadDiameterInvalidHostEntry OBJECT-TYPE
    SYNTAX      HomesteadDiameterInvalidHostEntry
    MAX-ACCESS  not-accessible
    STATUS      current
    DESCRIPTION "The total number of Diameter requests with an invalid Destination-Host."
    INDEX       { homesteadDiameterInvalidHostScope }
    ::= { homesteadDiameterInvalidHostTable 1 }

HomesteadDiameterInvalidHostEntry ::= SEQUENCE
{
  homesteadDiameterInvalidHostScope          INTEGER,
  homesteadDiameterInvalidHostCount          Unsigned32
}

homesteadDiameterInvalidHostScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadDiameterInvalidHostEntry 1 }

homesteadDiameterInvalidHostCount OBJECT-TYPE
    SYNTAX      Unsigned32
    MAX-ACCESS  read-only
    STATUS      current
    DESCRIPTION "The total number of Diameter requests with an invalid Destination-Host over the period."
    ::= { homesteadDiameterInvalidHostEntry 2 }

homesteadGroup OBJECT-GROUP
    OBJECTS {
      homesteadLatencyAverage,
      homesteadLatencyVariance,
      homesteadLatencyHWM,
      homesteadLatencyLWM,
      homesteadLatencyCount,
      homesteadHSSLatencyAverage,
      homesteadHSSLatencyVariance,
      homesteadHSSLatencyHWM,
      homesteadHSSLatencyLWM,
      homesteadHSSLatencyCount,
      homesteadCacheLatencyAverage,
      homesteadCacheLatencyVariance,
      homesteadCacheLatencyHWM,
      homesteadCacheLatencyLWM,
      homesteadCacheLatencyCount,
      homesteadDigestLatencyAverage,
      homesteadDigestLatencyVariance,
      homesteadDigestLatencyHWM,
      homesteadDigestLatencyLWM,
      homesteadDigestLatencyCount,
      homesteadSubscriptionLatencyAverage,
      homesteadSubscriptionLatencyVariance,
      homesteadSubscriptionLatencyHWM,
      homesteadSubscriptionLatencyLWM,
      homesteadSubscriptionLatencyCount,
      homesteadIncomingRequestsCount,
      homesteadRejectedOverloadCount,
      homesteadDiameterInvalidRealmCount,
      homesteadDiameterInvalidHostCount
    }
    STATUS      current
    DESCRIPTION "Statistics exposed by Homestead"
    ::= { projectClearwaterObjectGroups 4 }

-- Call Diversion AS Entries

cdivAsDiversionsTable OBJECT-TYPE
    SYNTAX SEQUENCE OF CdivAsDiversionsEntry
    MAX-ACCESS not-accessible
    STATUS current
    DESCRIPTION "Counts of diversion reasons by the Call Diversion AS over
                 the given period."
    ::= { callDiversionAs 1 }

cdivAsDiversionsEntry OBJECT-TYPE
    SYNTAX      CdivAsDiversionsEntry
    MAX-ACCESS  not-accessible
    STATUS      current
    DESCRIPTION "Counts of diversion reasons by the Call Diversion AS"
    INDEX       { cdivAsDiversionsScope }
    ::= { cdivAsDiversionsTable 1 }

CdivAsDiversionsEntry ::= SEQUENCE
{
  cdivAsDiversionsScope          INTEGER,
  cdivAsTotal                    Unsigned32,
  cdivAsUnconditional            Unsigned32,
  cdivAsBusy                     Unsigned32,
  cdivAsNotRegistered            Unsigned32,
  cdivAsNoAnswer                 Unsigned32,
  cdivAsNotReachable             Unsigned32
}

cdivAsDiversionsScope OBJECT-TYPE
    SYNTAX      INTEGER {
                  scopePrevious5SecondPeriod(1)
                }
    MAX-ACCESS  not-accessible
    STATUS      current
    DESCRIPTION "The period over which the statistics were collected."
    ::= { cdivAsDiversionsEntry 1 }

cdivAsTotal OBJECT-TYPE
    SYNTAX      Unsigned32
    MAX-ACCESS  read-only
    STATUS      current
    DESCRIPTION "The total number of requests that were diverted."
    ::= { cdivAsDiversionsEntry 2 }

cdivAsUnconditional OBJECT-TYPE
    SYNTAX      Unsigned32
    MAX-ACCESS  read-only
    STATUS      current
    DESCRIPTION "The number of requests that were unconditionally diverted."
    ::= { cdivAsDiversionsEntry 3 }

cdivAsBusy OBJECT-TYPE
    SYNTAX      Unsigned32
    MAX-ACCESS  read-only
    STATUS      current
    DESCRIPTION "The number of requests that were diverted due to a busy
                 condition."
    ::= { cdivAsDiversionsEntry 4 }

cdivAsNotRegistered OBJECT-TYPE
    SYNTAX      Unsigned32
    MAX-ACCESS  read-only
    STATUS      current
    DESCRIPTION "The number of requests that were diverted due to a not
                 registered condition."
    ::= { cdivAsDiversionsEntry 5 }

cdivAsNoAnswer OBJECT-TYPE
    SYNTAX      Unsigned32
    MAX-ACCESS  read-only
    STATUS      current
    DESCRIPTION "The number of requests that were diverted due to a no answer
                 condition."
    ::= { cdivAsDiversionsEntry 6 }

cdivAsNotReachable OBJECT-TYPE
    SYNTAX      Unsigned32
    MAX-ACCESS  read-only
    STATUS      current
    DESCRIPTION "The number of requests that were diverted due to a not
                 reachable condition."
    ::= { cdivAsDiversionsEntry 7 }

cdivAsIncomingSIPTransactionsTable OBJECT-TYPE
    SYNTAX SEQUENCE OF CdivAsIncomingSIPTransactionsEntry
    MAX-ACCESS not-accessible
    STATUS current
    DESCRIPTION "Counts the number of attempts, successes and failures
                 of incoming SIP transactions for the Call Diversion AS"
    ::= { callDiversionAs 2 }

cdivAsIncomingSIPTransactionsEntry OBJECT-TYPE
    SYNTAX      CdivAsIncomingSIPTransactionsEntry
    MAX-ACCESS  not-accessible
    STATUS      current
    DESCRIPTION "The number of attempts, successes and failures for
                 incoming SIP transactions for the Call Diversion AS"
    INDEX       { cdivAsIncomingSIPTransactionsTimeScope,
                  cdivAsIncomingSIPTransactionsRequestScope }
    ::= { cdivAsIncomingSIPTransactionsTable 1 }

CdivAsIncomingSIPTransactionsEntry ::= SEQUENCE
{
  cdivAsIncomingSIPTransactionsTimeScope      INTEGER,
  cdivAsIncomingSIPTransactionsRequestScope   INTEGER,
  cdivAsIncomingSIPTransactionsAttempts       Unsigned32,
  cdivAsIncomingSIPTransactionsSuccesses      Unsigned32,
  cdivAsIncomingSIPTransactionsFailures       Unsigned32
}

cdivAsIncomingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { cdivAsIncomingSIPTransactionsEntry 1 }

cdivAsIncomingSIPTransactionsRequestScope OBJECT-TYPE
    SYNTAX      RequestType
    MAX-ACCESS  not-accessible
    STATUS      current
    DESCRIPTION "The method type of the incoming transaction."
    ::= { cdivAsIncomingSIPTransactionsEntry 2 }

cdivAsIncomingSIPTransactionsAttempts OBJECT-TYPE
    SYNTAX      Unsigned32
    MAX-ACCESS  read-only
    STATUS      current
    DESCRIPTION "The number of incoming SIP transactions over the time period."
    ::= { cdivAsIncomingSIPTransactionsEntry 3 }

cdivAsIncomingSIPTransactionsSuccesses OBJECT-TYPE
    SYNTAX      Unsigned32
    MAX-ACCESS  read-only
    STATUS      current
    DESCRIPTION "The number of successful incoming SIP transactions over the
                 time period."
    ::= { cdivAsIncomingSIPTransactionsEntry 4 }

cdivAsIncomingSIPTransactionsFailures OBJECT-TYPE
    SYNTAX      Unsigned32
    MAX-ACCESS  read-only
    STATUS      current
    DESCRIPTION "The number of failed incoming SIP transactions over the
                 time period."
    ::= { cdivAsIncomingSIPTransactionsEntry 5 }

cdivAsOutgoingSIPTransactionsTable OBJECT-TYPE
    SYNTAX SEQUENCE OF CdivAsOutgoingSIPTransactionsEntry
    MAX-ACCESS not-accessible
    STATUS current
    DESCRIPTION "Counts the number of attempts, successes and failures
                 of outgoing SIP transactions for the Call Diversion AS."
    ::= { callDiversionAs 3 }

cdivAsOutgoingSIPTransactionsEntry OBJECT-TYPE
    SYNTAX      CdivAsOutgoingSIPTransactionsEntry
    MAX-ACCESS  not-accessible
    STATUS      current
    DESCRIPTION "The number of attempts, successes and failures for
                 outgoing SIP transactions for the Call Diversion AS."
    INDEX       { cdivAsOutgoingSIPTransactionsTimeScope,
                  cdivAsOutgoingSIPTransactionsRequestScope }
    ::= { cdivAsOutgoingSIPTransactionsTable 1 }

CdivAsOutgoingSIPTransactionsEntry ::= SEQUENCE
{
  cdivAsOutgoingSIPTransactionsTimeScope      INTEGER,
  cdivAsOutgoingSIPTransactionsRequestScope   INTEGER,
  cdivAsOutgoingSIPTransactionsAttempts       Unsigned32,
  cdivAsOutgoingSIPTransactionsSuccesses      Unsigned32,
  cdivAsOutgoingSIPTransactionsFailures       Unsigned32
}

cdivAsOutgoingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { cdivAsOutgoingSIPTransactionsEntry 1 }

cdivAsOutgoingSIPTransactionsRequestScope OBJECT-TYPE
    SYNTAX      RequestType
    MAX-ACCESS  not-accessible
    STATUS      current
    DESCRIPTION "The method type of the outgoing transaction."
    ::= { cdivAsOutgoingSIPTransactionsEntry 2 }

cdivAsOutgoingSIPTransactionsAttempts OBJECT-TYPE
    SYNTAX      Unsigned32
    MAX-ACCESS  read-only
    STATUS      current
    DESCRIPTION "The number of outgoing SIP transactions over the time period."
    ::= { cdivAsOutgoingSIPTransactionsEntry 3 }

cdivAsOutgoingSIPTransactionsSuccesses OBJECT-TYPE
    SYNTAX      Unsigned32
    MAX-ACCESS  read-only
    STATUS      current
    DESCRIPTION "The number of successful outgoing SIP transactions over the
                 time period."
    ::= { cdivAsOutgoingSIPTransactionsEntry 4 }

cdivAsOutgoingSIPTransactionsFailures OBJECT-TYPE
    SYNTAX      Unsigned32
    MAX-ACCESS  read-only
    STATUS      current
    DESCRIPTION "The number of failed outgoing SIP transactions over the
                 time period."
    ::= { cdivAsOutgoingSIPTransactionsEntry 5 }

callDiversionASGroup OBJECT-GROUP
    OBJECTS {
      cdivAsTotal,
      cdivAsUnconditional,
      cdivAsBusy,
      cdivAsNotRegistered,
      cdivAsNoAnswer,
      cdivAsNotReachable,
      cdivAsIncomingSIPTransactionsAttempts,
      cdivAsIncomingSIPTransactionsSuccesses,
      cdivAsIncomingSIPTransactionsFailures,
      cdivAsOutgoingSIPTransactionsAttempts,
      cdivAsOutgoingSIPTransactionsSuccesses,
      cdivAsOutgoingSIPTransactionsFailures
    }
    STATUS      current
    DESCRIPTION "Statistics exposed by Call Diversion AS"
    ::= { projectClearwaterObjectGroups 6 }

-- Memento Entries

mementoSIP OBJECT IDENTIFIER ::= { memento 1 }

mementoCallsRecordedTable OBJECT-TYPE
    SYNTAX SEQUENCE OF MementoCallsRecordedTableEntry
    MAX-ACCESS  not-accessible
    STATUS      current
    DESCRIPTION "Counts of call record creation outcomes for the given period."
    ::= { mementoSIP 1 }

mementoCallsRecordedTableEntry OBJECT-TYPE
    SYNTAX      MementoCallsRecordedTableEntry
    MAX-ACCESS  not-accessible
    STATUS      current
    DESCRIPTION "Counts of call record creation outcomes"
    INDEX       { mementoCallsRecordedScope }
    ::= { mementoCallsRecordedTable 1 }

MementoCallsRecordedTableEntry ::= SEQUENCE
{
    mementoCallsRecordedScope            INTEGER,
    mementoCompletedCallsRecorded        Unsigned32,
    mementoFailedCallsRecorded           Unsigned32,
    mementoCallsNotRecordedDueToOverload Unsigned32
}

mementoCallsRecordedScope OBJECT-TYPE
    SYNTAX      INTEGER {
                  scopePrevious5SecondPeriod(1)
                }
    MAX-ACCESS  not-accessible
    STATUS      current
    DESCRIPTION "The period over which the statistics were collected."
    ::= { mementoCallsRecordedTableEntry 1 }

mementoCompletedCallsRecorded OBJECT-TYPE
    SYNTAX      Unsigned32
    MAX-ACCESS  read-only
    STATUS      current
    DESCRIPTION "The total number of successful calls recorded."
    ::= { mementoCallsRecordedTableEntry 2 }

mementoFailedCallsRecorded OBJECT-TYPE
    SYNTAX      Unsigned32
    MAX-ACCESS  read-only
    STATUS      current
    DESCRIPTION "The total number of failed call attempts recorded."
    ::= { mementoCallsRecordedTableEntry 3 }

mementoCallsNotRecordedDueToOverload OBJECT-TYPE
    SYNTAX      Unsigned32
    MAX-ACCESS  read-only
    STATUS      current
    DESCRIPTION "The total number of call records dropped due to overload."
    ::= { mementoCallsRecordedTableEntry 4 }

mementoSIPCassandraReadLatencyTable OBJECT-TYPE
    SYNTAX SEQUENCE OF MementoSIPCassandraReadLatencyEntry
    MAX-ACCESS not-accessible
    STATUS current
    DESCRIPTION "The average, variance, LWM and HWM of Cassandra database read
                 latency reported by the SIP AS component  Latency measured in
                 microseconds"
    ::= { mementoSIP 2 }

mementoSIPCassandraReadLatencyEntry OBJECT-TYPE
    SYNTAX      MementoSIPCassandraReadLatencyEntry
    MAX-ACCESS  not-accessible
    STATUS      current
    DESCRIPTION "The average, variance, LWM and HWM of Cassandra database read
                 latency reported by the SIP AS component"
    INDEX       { mementoSIPCassandraReadLatencyScope }
    ::= { mementoSIPCassandraReadLatencyTable 1 }

MementoSIPCassandraReadLatencyEntry ::= SEQUENCE
{
  mementoSIPCassandraReadLatencyScope          INTEGER,
  mementoSIPCassandraReadLatencyAverage        Unsigned32,
  mementoSIPCassandraReadLatencyVariance       Unsigned32,
  mementoSIPCassandraReadLatencyHWM            Unsigned32,
  mementoSIPCassandraReadLatencyLWM            Unsigned32,
  mementoSIPCassandraReadLatencyCount          Unsigned32
}

mementoSIPCassandraReadLatencyScope OBJECT-TYPE
    SYNTAX      INTEGER {
                  scopePrevious5SecondPeriod(1)
                }
    MAX-ACCESS  not-accessible
    STATUS      current
    DESCRIPTION "The period over which the statistics were collected."
    ::= { mementoSIPCassandraReadLatencyEntry 1 }

mementoSIPCassandraReadLatencyAverage OBJECT-TYPE
    SYNTAX      Unsigned32
    MAX-ACCESS  read-only
    STATUS      current
    DESCRIPTION "The average latency over the period."
    ::= { mementoSIPCassandraReadLatencyEntry 2 }

mementoSIPCassandraReadLatencyVariance OBJECT-TYPE
    SYNTAX      Unsigned32
    MAX-ACCESS  read-only
    STATUS      current
    DESCRIPTION "The variance of the latency over the period."
    ::= { mementoSIPCassandraReadLatencyEntry 3 }

mementoSIPCassandraReadLatencyHWM OBJECT-TYPE
    SYNTAX      Unsigned32
    MAX-ACCESS  read-only
    STATUS      current
    DESCRIPTION "The highest latency over the period."
    ::= { mementoSIPCassandraReadLatencyEntry 4 }

mementoSIPCassandraReadLatencyLWM OBJECT-TYPE
    SYNTAX      Unsigned32
    MAX-ACCESS  read-only
    STATUS      current
    DESCRIPTION "The lowest latency over the period."
    ::= { mementoSIPCassandraReadLatencyEntry 5 }

mementoSIPCassandraReadLatencyCount OBJECT-TYPE
    SYNTAX      Unsigned32
    MAX-ACCESS  read-only
    STATUS      current
    DESCRIPTION "The total number of reads over the period."
    ::= { mementoSIPCassandraReadLatencyEntry 6 }

mementoSIPCassandraWriteLatencyTable OBJECT-TYPE
    SYNTAX SEQUENCE OF MementoSIPCassandraWriteLatencyTableEntry
    MAX-ACCESS not-accessible
    STATUS current
    DESCRIPTION "The average, variance, LWM and HWM of Cassandra database write
                 latency reported by the SIP AS component.  Latency measured in
                 microseconds"
    ::= { mementoSIP 3 }

mementoSIPCassandraWriteLatencyEntry OBJECT-TYPE
    SYNTAX      MementoSIPCassandraWriteLatencyTableEntry
    MAX-ACCESS  not-accessible
    STATUS      current
    DESCRIPTION "The average, variance, LWM and HWM of Cassandra database write
                 latency reported by the SIP AS component."
    INDEX       { mementoSIPCassandraWriteLatencyScope }
    ::= { mementoSIPCassandraWriteLatencyTable 1 }

MementoSIPCassandraWriteLatencyTableEntry ::= SEQUENCE
{
  mementoSIPCassandraWriteLatencyScope          INTEGER,
  mementoSIPCassandraWriteLatencyAverage        Unsigned32,
  mementoSIPCassandraWriteLatencyVariance       Unsigned32,
  mementoSIPCassandraWriteLatencyHWM            Unsigned32,
  mementoSIPCassandraWriteLatencyLWM            Unsigned32,
  mementoSIPCassandraWriteLatencyCount          Unsigned32
}

mementoSIPCassandraWriteLatencyScope OBJECT-TYPE
    SYNTAX      INTEGER {
                  scopePrevious5SecondPeriod(1)
                }
    MAX-ACCESS  not-accessible
    STATUS      current
    DESCRIPTION "The period over which the statistics were collected."
    ::= { mementoSIPCassandraWriteLatencyEntry 1 }

mementoSIPCassandraWriteLatencyAverage OBJECT-TYPE
    SYNTAX      Unsigned32
    MAX-ACCESS  read-only
    STATUS      current
    DESCRIPTION "The average latency over the period."
    ::= { mementoSIPCassandraWriteLatencyEntry 2 }

mementoSIPCassandraWriteLatencyVariance OBJECT-TYPE
    SYNTAX      Unsigned32
    MAX-ACCESS  read-only
    STATUS      current
    DESCRIPTION "The variance of the latency over the period."
    ::= { mementoSIPCassandraWriteLatencyEntry 3 }

mementoSIPCassandraWriteLatencyHWM OBJECT-TYPE
    SYNTAX      Unsigned32
    MAX-ACCESS  read-only
    STATUS      current
    DESCRIPTION "The highest latency over the period."
    ::= { mementoSIPCassandraWriteLatencyEntry 4 }

mementoSIPCassandraWriteLatencyLWM OBJECT-TYPE
    SYNTAX      Unsigned32
    MAX-ACCESS  read-only
    STATUS      current
    DESCRIPTION "The lowest latency over the period."
    ::= { mementoSIPCassandraWriteLatencyEntry 5 }

mementoSIPCassandraWriteLatencyCount OBJECT-TYPE
    SYNTAX      Unsigned32
    MAX-ACCESS  read-only
    STATUS      current
    DESCRIPTION "The total number of writes over the period."
    ::= { mementoSIPCassandraWriteLatencyEntry 6 }

mementoIncomingSIPTransactionsTable OBJECT-TYPE
    SYNTAX SEQUENCE OF MementoIncomingSIPTransactionsEntry
    MAX-ACCESS not-accessible
    STATUS current
    DESCRIPTION "Counts the number of attempts, successes and failures
                 of incoming SIP transactions for Memento"
    ::= { mementoSIP 4 }

mementoIncomingSIPTransactionsEntry OBJECT-TYPE
    SYNTAX      MementoIncomingSIPTransactionsEntry
    MAX-ACCESS  not-accessible
    STATUS      current
    DESCRIPTION "The number of attempts, successes and failures for
                 incoming SIP transactions for Memento"
    INDEX       { mementoIncomingSIPTransactionsTimeScope,
                  mementoIncomingSIPTransactionsRequestScope }
    ::= { mementoIncomingSIPTransactionsTable 1 }

MementoIncomingSIPTransactionsEntry ::= SEQUENCE
{
  mementoIncomingSIPTransactionsTimeScope      INTEGER,
  mementoIncomingSIPTransactionsRequestScope   INTEGER,
  mementoIncomingSIPTransactionsAttempts       Unsigned32,
  mementoIncomingSIPTransactionsSuccesses      Unsigned32,
  mementoIncomingSIPTransactionsFailures       Unsigned32
}

mementoIncomingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { mementoIncomingSIPTransactionsEntry 1 }

mementoIncomingSIPTransactionsRequestScope OBJECT-TYPE
    SYNTAX      RequestType
    MAX-ACCESS  not-accessible
    STATUS      current
    DESCRIPTION "The method type of the incoming transaction."
    ::= { mementoIncomingSIPTransactionsEntry 2 }

mementoIncomingSIPTransactionsAttempts OBJECT-TYPE
    SYNTAX      Unsigned32
    MAX-ACCESS  read-only
    STATUS      current
    DESCRIPTION "The number of incoming SIP transactions over the time period."
    ::= { mementoIncomingSIPTransactionsEntry 3 }

mementoIncomingSIPTransactionsSuccesses OBJECT-TYPE
    SYNTAX      Unsigned32
    MAX-ACCESS  read-only
    STATUS      current
    DESCRIPTION "The number of successful incoming SIP transactions over the
                 time period."
    ::= { mementoIncomingSIPTransactionsEntry 4 }

mementoIncomingSIPTransactionsFailures OBJECT-TYPE
    SYNTAX      Unsigned32
    MAX-ACCESS  read-only
    STATUS      current
    DESCRIPTION "The number of failed incoming SIP transactions over the
                 time period."
    ::= { mementoIncomingSIPTransactionsEntry 5 }

mementoOutgoingSIPTransactionsTable OBJECT-TYPE
    SYNTAX SEQUENCE OF MementoOutgoingSIPTransactionsEntry
    MAX-ACCESS not-accessible
    STATUS current
    DESCRIPTION "Counts the number of attempts, successes and failures
                 of outgoing SIP transactions for Memento"
    ::= { mementoSIP 5 }

mementoOutgoingSIPTransactionsEntry OBJECT-TYPE
    SYNTAX      MementoOutgoingSIPTransactionsEntry
    MAX-ACCESS  not-accessible
    STATUS      current
    DESCRIPTION "The number of attempts, successes and failures for
                 outgoing SIP transactions for Memento"
    INDEX       { mementoOutgoingSIPTransactionsTimeScope,
                  mementoOutgoingSIPTransactionsRequestScope }
    ::= { mementoOutgoingSIPTransactionsTable 1 }

MementoOutgoingSIPTransactionsEntry ::= SEQUENCE
{
  mementoOutgoingSIPTransactionsTimeScope      INTEGER,
  mementoOutgoingSIPTransactionsRequestScope   INTEGER,
  mementoOutgoingSIPTransactionsAttempts       Unsigned32,
  mementoOutgoingSIPTransactionsSuccesses      Unsigned32,
  mementoOutgoingSIPTransactionsFailures       Unsigned32
}

mementoOutgoingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { mementoOutgoingSIPTransactionsEntry 1 }

mementoOutgoingSIPTransactionsRequestScope OBJECT-TYPE
    SYNTAX      RequestType
    MAX-ACCESS  not-accessible
    STATUS      current
    DESCRIPTION "The method type of the outgoing transaction."
    ::= { mementoOutgoingSIPTransactionsEntry 2 }

mementoOutgoingSIPTransactionsAttempts OBJECT-TYPE
    SYNTAX      Unsigned32
    MAX-ACCESS  read-only
    STATUS      current
    DESCRIPTION "The number of outgoing SIP transactions over the time period."
    ::= { mementoOutgoingSIPTransactionsEntry 3 }

mementoOutgoingSIPTransactionsSuccesses OBJECT-TYPE
    SYNTAX      Unsigned32
    MAX-ACCESS  read-only
    STATUS      current
    DESCRIPTION "The number of successful outgoing SIP transactions over the
                 time period."
    ::= { mementoOutgoingSIPTransactionsEntry 4 }

mementoOutgoingSIPTransactionsFailures OBJECT-TYPE
    SYNTAX      Unsigned32
    MAX-ACCESS  read-only
    STATUS      current
    DESCRIPTION "The number of failed outgoing SIP transactions over the
                 time period."
    ::= { mementoOutgoingSIPTransactionsEntry 5 }

mementoHTTP OBJECT IDENTIFIER ::= { memento 2 }

mementoHTTPRequestTable OBJECT-TYPE
    SYNTAX SEQUENCE OF MementoHTTPRequestTableEntry
    MAX-ACCESS  not-accessible
    STATUS      current
    DESCRIPTION "Counts of HTTP requests and their outcomes for the given
                 period"
    ::= { mementoHTTP 1 }

mementoHTTPRequestTableEntry OBJECT-TYPE
    SYNTAX      MementoHTTPRequestTableEntry
    MAX-ACCESS  not-accessible
    STATUS      current
    DESCRIPTION "Counts of HTTP requests and their outcomes"
    INDEX       { mementoHTTPRequestScope }
    ::= { mementoHTTPRequestTable 1 }

MementoHTTPRequestTableEntry ::= SEQUENCE
{
    mementoHTTPRequestScope            INTEGER,
    mementoHTTPRequestCount            Unsigned32,
    mementoHTTPRejectedDueToOverload   Unsigned32
}

mementoHTTPRequestScope OBJECT-TYPE
    SYNTAX      INTEGER {
                  scopePrevious5SecondPeriod(1)
                }
    MAX-ACCESS  not-accessible
    STATUS      current
    DESCRIPTION "The period over which the statistics were collected."
    ::= { mementoHTTPRequestTableEntry 1 }

mementoHTTPRequestCount OBJECT-TYPE
    SYNTAX      Unsigned32
    MAX-ACCESS  read-only
    STATUS      current
    DESCRIPTION "The total number of HTTP requests received."
    ::= { mementoHTTPRequestTableEntry 2 }

mementoHTTPRejectedDueToOverload OBJECT-TYPE
    SYNTAX      Unsigned32
    MAX-ACCESS  read-only
    STATUS      current
    DESCRIPTION "The total number of HTTP requests rejected due to overload."
    ::= { mementoHTTPRequestTableEntry 3 }

mementoHTTPRequestLatencyTable OBJECT-TYPE
    SYNTAX SEQUENCE OF MementoHTTPRequestLatencyTableEntry
    MAX-ACCESS not-accessible
    STATUS current
    DESCRIPTION "Latency of HTTP call record retrieval requests over the given
                 period.  Latency measured in microseconds"
    ::= { mementoHTTP 2 }

mementoHTTPRequestLatencyEntry OBJECT-TYPE
    SYNTAX      MementoHTTPRequestLatencyTableEntry
    MAX-ACCESS  not-accessible
    STATUS      current
    DESCRIPTION "The average, variance, LWM and HWM of HTTP call retrieval latency"
    INDEX       { mementoHTTPRequestLatencyScope }
    ::= { mementoHTTPRequestLatencyTable 1 }

MementoHTTPRequestLatencyTableEntry ::= SEQUENCE
{
  mementoHTTPRequestLatencyScope          INTEGER,
  mementoHTTPRequestLatencyAverage        Unsigned32,
  mementoHTTPRequestLatencyVariance       Unsigned32,
  mementoHTTPRequestLatencyHWM            Unsigned32,
  mementoHTTPRequestLatencyLWM            Unsigned32,
  mementoHTTPRequestLatencyCount          Unsigned32
}

mementoHTTPRequestLatencyScope OBJECT-TYPE
    SYNTAX      INTEGER {
                  scopePrevious5SecondPeriod(1)
                }
    MAX-ACCESS  not-accessible
    STATUS      current
    DESCRIPTION "The period over which the statistics were collected."
    ::= { mementoHTTPRequestLatencyEntry 1 }

mementoHTTPRequestLatencyAverage OBJECT-TYPE
    SYNTAX      Unsigned32
    MAX-ACCESS  read-only
    STATUS      current
    DESCRIPTION "The average latency over the period."
    ::= { mementoHTTPRequestLatencyEntry 2 }

mementoHTTPRequestLatencyVariance OBJECT-TYPE
    SYNTAX      Unsigned32
    MAX-ACCESS  read-only
    STATUS      current
    DESCRIPTION "The variance of the latency over the period."
    ::= { mementoHTTPRequestLatencyEntry 3 }

mementoHTTPRequestLatencyHWM OBJECT-TYPE
    SYNTAX      Unsigned32
    MAX-ACCESS  read-only
    STATUS      current
    DESCRIPTION "The highest latency over the period."
    ::= { mementoHTTPRequestLatencyEntry 4 }

mementoHTTPRequestLatencyLWM OBJECT-TYPE
    SYNTAX      Unsigned32
    MAX-ACCESS  read-only
    STATUS      current
    DESCRIPTION "The lowest latency over the period."
    ::= { mementoHTTPRequestLatencyEntry 5 }

mementoHTTPRequestLatencyCount OBJECT-TYPE
    SYNTAX      Unsigned32
    MAX-ACCESS  read-only
    STATUS      current
    DESCRIPTION "The total requests over the period."
    ::= { mementoHTTPRequestLatencyEntry 6 }

mementoHTTPCassandraReadLatencyTable OBJECT-TYPE
    SYNTAX SEQUENCE OF MementoHTTPCassandraReadLatencyTableEntry
    MAX-ACCESS not-accessible
    STATUS current
    DESCRIPTION "The average, variance, LWM and HWM of Cassandra database read
                 latency reported by the HTTP component.  Latency measured in
                 microseconds"
    ::= { mementoHTTP 3 }

mementoHTTPCassandraReadLatencyEntry OBJECT-TYPE
    SYNTAX      MementoHTTPCassandraReadLatencyTableEntry
    MAX-ACCESS  not-accessible
    STATUS      current
    DESCRIPTION "The average, variance, LWM and HWM of Cassandra database read
                 latency reported by the HTTP component."
    INDEX       { mementoHTTPCassandraReadLatencyScope }
    ::= { mementoHTTPCassandraReadLatencyTable 1 }

MementoHTTPCassandraReadLatencyTableEntry ::= SEQUENCE
{
  mementoHTTPCassandraReadLatencyScope          INTEGER,
  mementoHTTPCassandraReadLatencyAverage        Unsigned32,
  mementoHTTPCassandraReadLatencyVariance       Unsigned32,
  mementoHTTPCassandraReadLatencyHWM            Unsigned32,
  mementoHTTPCassandraReadLatencyLWM            Unsigned32,
  mementoHTTPCassandraReadLatencyCount          Unsigned32
}

mementoHTTPCassandraReadLatencyScope OBJECT-TYPE
    SYNTAX      INTEGER {
                  scopePrevious5SecondPeriod(1)
                }
    MAX-ACCESS  not-accessible
    STATUS      current
    DESCRIPTION "The period over which the statistics were collected."
    ::= { mementoHTTPCassandraReadLatencyEntry 1 }

mementoHTTPCassandraReadLatencyAverage OBJECT-TYPE
    SYNTAX      Unsigned32
    MAX-ACCESS  read-only
    STATUS      current
    DESCRIPTION "The average latency over the period."
    ::= { mementoHTTPCassandraReadLatencyEntry 2 }

mementoHTTPCassandraReadLatencyVariance OBJECT-TYPE
    SYNTAX      Unsigned32
    MAX-ACCESS  read-only
    STATUS      current
    DESCRIPTION "The variance of the latency over the period."
    ::= { mementoHTTPCassandraReadLatencyEntry 3 }

mementoHTTPCassandraReadLatencyHWM OBJECT-TYPE
    SYNTAX      Unsigned32
    MAX-ACCESS  read-only
    STATUS      current
    DESCRIPTION "The highest latency over the period."
    ::= { mementoHTTPCassandraReadLatencyEntry 4 }

mementoHTTPCassandraReadLatencyLWM OBJECT-TYPE
    SYNTAX      Unsigned32
    MAX-ACCESS  read-only
    STATUS      current
    DESCRIPTION "The lowest latency over the period."
    ::= { mementoHTTPCassandraReadLatencyEntry 5 }

mementoHTTPCassandraReadLatencyCount OBJECT-TYPE
    SYNTAX      Unsigned32
    MAX-ACCESS  read-only
    STATUS      current
    DESCRIPTION "The total number of reads over the period."
    ::= { mementoHTTPCassandraReadLatencyEntry 6 }

mementoRetrievedCallRecordSizeTable OBJECT-TYPE
    SYNTAX SEQUENCE OF MementoRetrievedCallRecordSizeTableEntry
    MAX-ACCESS not-accessible
    STATUS current
    DESCRIPTION "Average, variance, HWM and LWM of the size (in kB) of call records
                 retrieved from the store."
    ::= { mementoHTTP 4 }

mementoRetrievedCallRecordSizeEntry OBJECT-TYPE
    SYNTAX      MementoRetrievedCallRecordSizeTableEntry
    MAX-ACCESS  not-accessible
    STATUS      current
    DESCRIPTION "Average, variance, HWM and LWM of the size (in kB) of call records
                 retrieved from the store."
    INDEX       { mementoRetrievedCallRecordSizeScope }
    ::= { mementoRetrievedCallRecordSizeTable 1 }

MementoRetrievedCallRecordSizeTableEntry ::= SEQUENCE
{
  mementoRetrievedCallRecordSizeScope          INTEGER,
  mementoRetrievedCallRecordSizeAverage        Unsigned32,
  mementoRetrievedCallRecordSizeVariance       Unsigned32,
  mementoRetrievedCallRecordSizeHWM            Unsigned32,
  mementoRetrievedCallRecordSizeLWM            Unsigned32,
  mementoRetrievedCallRecordSizeCount          Unsigned32
}

mementoRetrievedCallRecordSizeScope OBJECT-TYPE
    SYNTAX      INTEGER {
                  scopePrevious5SecondPeriod(1)
                }
    MAX-ACCESS  not-accessible
    STATUS      current
    DESCRIPTION "The period over which the statistics were collected."
    ::= { mementoRetrievedCallRecordSizeEntry 1 }

mementoRetrievedCallRecordSizeAverage OBJECT-TYPE
    SYNTAX      Unsigned32
    MAX-ACCESS  read-only
    STATUS      current
    DESCRIPTION "The average size over the period."
    ::= { mementoRetrievedCallRecordSizeEntry 2 }

mementoRetrievedCallRecordSizeVariance OBJECT-TYPE
    SYNTAX      Unsigned32
    MAX-ACCESS  read-only
    STATUS      current
    DESCRIPTION "The variance of the size over the period."
    ::= { mementoRetrievedCallRecordSizeEntry 3 }

mementoRetrievedCallRecordSizeHWM OBJECT-TYPE
    SYNTAX      Unsigned32
    MAX-ACCESS  read-only
    STATUS      current
    DESCRIPTION "The highest size over the period."
    ::= { mementoRetrievedCallRecordSizeEntry 4 }

mementoRetrievedCallRecordSizeLWM OBJECT-TYPE
    SYNTAX      Unsigned32
    MAX-ACCESS  read-only
    STATUS      current
    DESCRIPTION "The lowest size over the period."
    ::= { mementoRetrievedCallRecordSizeEntry 5 }

mementoRetrievedCallRecordSizeCount OBJECT-TYPE
    SYNTAX      Unsigned32
    MAX-ACCESS  read-only
    STATUS      current
    DESCRIPTION "The total number of call lists retrieved over the period."
    ::= { mementoRetrievedCallRecordSizeEntry 6 }

mementoRetrievedCallRecordLengthTable OBJECT-TYPE
    SYNTAX SEQUENCE OF MementoRetrievedCallRecordLengthTableEntry
    MAX-ACCESS not-accessible
    STATUS current
    DESCRIPTION "Average, variance, HWM and LWM of the length (# of records) of call
                 records retrieved from the store."
    ::= { mementoHTTP 5 }

mementoRetrievedCallRecordLengthEntry OBJECT-TYPE
    SYNTAX      MementoRetrievedCallRecordLengthTableEntry
    MAX-ACCESS  not-accessible
    STATUS      current
    DESCRIPTION "Average, variance, HWM and LWM of the length (# of records) of call
                 records retrieved from the store."
    INDEX       { mementoRetrievedCallRecordLengthScope }
    ::= { mementoRetrievedCallRecordLengthTable 1 }

MementoRetrievedCallRecordLengthTableEntry ::= SEQUENCE
{
  mementoRetrievedCallRecordLengthScope          INTEGER,
  mementoRetrievedCallRecordLengthAverage        Unsigned32,
  mementoRetrievedCallRecordLengthVariance       Unsigned32,
  mementoRetrievedCallRecordLengthHWM            Unsigned32,
  mementoRetrievedCallRecordLengthLWM            Unsigned32,
  mementoRetrievedCallRecordLengthCount          Unsigned32
}

mementoRetrievedCallRecordLengthScope OBJECT-TYPE
    SYNTAX      INTEGER {
                  scopePrevious5SecondPeriod(1)
                }
    MAX-ACCESS  not-accessible
    STATUS      current
    DESCRIPTION "The period over which the statistics were collected."
    ::= { mementoRetrievedCallRecordLengthEntry 1 }

mementoRetrievedCallRecordLengthAverage OBJECT-TYPE
    SYNTAX      Unsigned32
    MAX-ACCESS  read-only
    STATUS      current
    DESCRIPTION "The average latency over the period."
    ::= { mementoRetrievedCallRecordLengthEntry 2 }

mementoRetrievedCallRecordLengthVariance OBJECT-TYPE
    SYNTAX      Unsigned32
    MAX-ACCESS  read-only
    STATUS      current
    DESCRIPTION "The variance of the latency over the period."
    ::= { mementoRetrievedCallRecordLengthEntry 3 }

mementoRetrievedCallRecordLengthHWM OBJECT-TYPE
    SYNTAX      Unsigned32
    MAX-ACCESS  read-only
    STATUS      current
    DESCRIPTION "The highest latency over the period."
    ::= { mementoRetrievedCallRecordLengthEntry 4 }

mementoRetrievedCallRecordLengthLWM OBJECT-TYPE
    SYNTAX      Unsigned32
    MAX-ACCESS  read-only
    STATUS      current
    DESCRIPTION "The lowest latency over the period."
    ::= { mementoRetrievedCallRecordLengthEntry 5 }

mementoRetrievedCallRecordLengthCount OBJECT-TYPE
    SYNTAX      Unsigned32
    MAX-ACCESS  read-only
    STATUS      current
    DESCRIPTION "The total number of call lists retrieved over the period."
    ::= { mementoRetrievedCallRecordLengthEntry 6 }

mementoAuthProxy OBJECT IDENTIFIER ::= { memento 3 }

mementoConnectedHomesteadsTable OBJECT-TYPE
    SYNTAX SEQUENCE OF MementoConnectedHomesteadsEntry
    MAX-ACCESS not-accessible
    STATUS current
    DESCRIPTION "Statistics for each connected upstream Homestead node"
    ::= { mementoAuthProxy 1 }

mementoConnectedHomesteadsEntry OBJECT-TYPE
    SYNTAX MementoConnectedHomesteadsEntry
    MAX-ACCESS not-accessible
    STATUS current
    DESCRIPTION "Statistics for a single connected upstream Homestead"
    INDEX { mementoHomesteadInetAddrType,
            mementoHomesteadInetAddr      }
    ::= { mementoConnectedHomesteadsTable 1 }

MementoConnectedHomesteadsEntry ::= SEQUENCE
{
  mementoHomesteadInetAddrType    InetAddressType,
  mementoHomesteadInetAddr        InetAddress,
  mementoHomesteadConnectionCount Unsigned32
}

mementoHomesteadInetAddrType OBJECT-TYPE
    SYNTAX      InetAddressType
    MAX-ACCESS  not-accessible
    STATUS      current
    DESCRIPTION "Inet address type of the upstream Homestead"
    ::= { mementoConnectedHomesteadsEntry 1 }

mementoHomesteadInetAddr OBJECT-TYPE
    SYNTAX      InetAddress (SIZE (1..16))
    MAX-ACCESS  not-accessible
    STATUS      current
    DESCRIPTION "Inet address of the upstream Homestead"
    ::= { mementoConnectedHomesteadsEntry 2 }

mementoHomesteadConnectionCount OBJECT-TYPE
    SYNTAX      Unsigned32
    MAX-ACCESS  read-only
    STATUS      current
    DESCRIPTION "Current count of TCP connections from Memento to the
                 Homestead node, may include connections in setting-
                 up state"
    ::= { mementoConnectedHomesteadsEntry 3 }

mementoAuthAttemptTable OBJECT-TYPE
    SYNTAX SEQUENCE OF MementoAuthAttemptTableEntry
    MAX-ACCESS not-accessible
    STATUS current
    DESCRIPTION "Counts of authentication attempts over the given period."
    ::= { mementoAuthProxy 2 }

mementoAuthAttemptEntry OBJECT-TYPE
    SYNTAX      MementoAuthAttemptTableEntry
    MAX-ACCESS  not-accessible
    STATUS      current
    DESCRIPTION "Counts of authentication attempts over the given period."
    INDEX       { mementoAuthAttemptScope }
    ::= { mementoAuthAttemptTable 1 }

MementoAuthAttemptTableEntry ::= SEQUENCE
{
  mementoAuthAttemptScope          INTEGER,
  mementoAuthChallengeCount        Unsigned32,
  mementoAuthAttemptCount          Unsigned32,
  mementoAuthSuccessCount          Unsigned32,
  mementoAuthFailureCount          Unsigned32,
  mementoAuthStaleCount            Unsigned32
}

mementoAuthAttemptScope OBJECT-TYPE
    SYNTAX      INTEGER {
                  scopePrevious5SecondPeriod(1)
                }
    MAX-ACCESS  not-accessible
    STATUS      current
    DESCRIPTION "The period over which the statistics were collected."
    ::= { mementoAuthAttemptEntry 1 }

mementoAuthChallengeCount OBJECT-TYPE
    SYNTAX      Unsigned32
    MAX-ACCESS  read-only
    STATUS      current
    DESCRIPTION "The count of authentication challenges requested."
    ::= { mementoAuthAttemptEntry 2 }

mementoAuthAttemptCount OBJECT-TYPE
    SYNTAX      Unsigned32
    MAX-ACCESS  read-only
    STATUS      current
    DESCRIPTION "The count of authentication attempts."
    ::= { mementoAuthAttemptEntry 3 }

mementoAuthSuccessCount OBJECT-TYPE
    SYNTAX      Unsigned32
    MAX-ACCESS  read-only
    STATUS      current
    DESCRIPTION "The count of successful authentications."
    ::= { mementoAuthAttemptEntry 4 }

mementoAuthFailureCount OBJECT-TYPE
    SYNTAX      Unsigned32
    MAX-ACCESS  read-only
    STATUS      current
    DESCRIPTION "The count of authentication failures due to incorrect credentials."
    ::= { mementoAuthAttemptEntry 5 }

mementoAuthStaleCount OBJECT-TYPE
    SYNTAX      Unsigned32
    MAX-ACCESS  read-only
    STATUS      current
    DESCRIPTION "The count of authentication failures due to stale challenges."
    ::= { mementoAuthAttemptEntry 6 }

mementoDiskUsage OBJECT IDENTIFIER::= { memento 4 }

mementoDatabaseDiskUsage OBJECT-TYPE
    SYNTAX      Unsigned32
    MAX-ACCESS  read-only
    STATUS      current
    DESCRIPTION "Current Memento database disk usage."
    ::= { mementoDiskUsage 1 }

mementoGroup OBJECT-GROUP
    OBJECTS {
        mementoCompletedCallsRecorded,
        mementoFailedCallsRecorded,
        mementoCallsNotRecordedDueToOverload,
        mementoHTTPRequestCount,
        mementoHTTPRejectedDueToOverload,
        mementoHTTPRequestLatencyAverage,
        mementoHTTPRequestLatencyVariance,
        mementoHTTPRequestLatencyHWM,
        mementoHTTPRequestLatencyLWM,
        mementoHTTPRequestLatencyCount,
        mementoSIPCassandraReadLatencyAverage,
        mementoSIPCassandraReadLatencyVariance,
        mementoSIPCassandraReadLatencyHWM,
        mementoSIPCassandraReadLatencyLWM,
        mementoSIPCassandraReadLatencyCount,
        mementoSIPCassandraWriteLatencyAverage,
        mementoSIPCassandraWriteLatencyVariance,
        mementoSIPCassandraWriteLatencyHWM,
        mementoSIPCassandraWriteLatencyLWM,
        mementoSIPCassandraWriteLatencyCount,
        mementoHTTPCassandraReadLatencyAverage,
        mementoHTTPCassandraReadLatencyVariance,
        mementoHTTPCassandraReadLatencyHWM,
        mementoHTTPCassandraReadLatencyLWM,
        mementoHTTPCassandraReadLatencyCount,
        mementoRetrievedCallRecordSizeAverage,
        mementoRetrievedCallRecordSizeVariance,
        mementoRetrievedCallRecordSizeHWM,
        mementoRetrievedCallRecordSizeLWM,
        mementoRetrievedCallRecordSizeCount,
        mementoRetrievedCallRecordLengthAverage,
        mementoRetrievedCallRecordLengthVariance,
        mementoRetrievedCallRecordLengthHWM,
        mementoRetrievedCallRecordLengthLWM,
        mementoRetrievedCallRecordLengthCount,
        mementoHomesteadConnectionCount,
        mementoAuthChallengeCount,
        mementoAuthAttemptCount,
        mementoAuthSuccessCount,
        mementoAuthFailureCount,
        mementoAuthStaleCount,
        mementoDatabaseDiskUsage,
        mementoIncomingSIPTransactionsAttempts,
        mementoIncomingSIPTransactionsSuccesses,
        mementoIncomingSIPTransactionsFailures,
        mementoOutgoingSIPTransactionsAttempts,
        mementoOutgoingSIPTransactionsSuccesses,
        mementoOutgoingSIPTransactionsFailures
    }
    STATUS      current
    DESCRIPTION "Statistics exposed by Memento"
    ::= { projectClearwaterObjectGroups 5 }

-- Astaire Entries

astaireBucketsNeedingResync OBJECT-TYPE
    SYNTAX      Unsigned32
    MAX-ACCESS  read-only
    STATUS      current
    DESCRIPTION "Count of buckets needing to be synchronized for the current
                 resynchronization operation.  Set to 0 if there is no outstanding
                 resynchronization operation - in particular, if it has already
                 completed."
    ::= { astaire 1 }

astaireBucketsResynchronized OBJECT-TYPE
    SYNTAX      Unsigned32
    MAX-ACCESS  read-only
    STATUS      current
    DESCRIPTION "Number of buckets already resynchronized during the current
                 resynchronization operation.  Set to 0 if there is no outstanding
                 resynchronization operation - in particular, if it has already
                 completed."
    ::= { astaire 2 }

astaireEntriesResynchronized OBJECT-TYPE
    SYNTAX      Unsigned32
    MAX-ACCESS  read-only
    STATUS      current
    DESCRIPTION "Number of entries already resynchronized during the current
                 resynchronization operation.  Set to 0 if there is no outstanding
                 resynchronization operation - in particular, if it has already
                 completed."
    ::= { astaire 3 }

astaireDataResynchronized OBJECT-TYPE
    SYNTAX      Unsigned32
    MAX-ACCESS  read-only
    STATUS      current
    DESCRIPTION "Amout of data (in bytes) already resynchronized during the current
                 resynchronization operation.  Set to 0 if there is no outstanding
                 resynchronization operation - in particular, if it has already
                 completed."
    ::= { astaire 4 }

astaireBandwidthTable OBJECT-TYPE
    SYNTAX SEQUENCE OF AstaireBandwidthTableEntry
    MAX-ACCESS  not-accessible
    STATUS      current
    DESCRIPTION "Resynchronization bandwidth for the given period."
    ::= { astaire 5 }

astaireBandwidthTableEntry OBJECT-TYPE
    SYNTAX      AstaireBandwidthTableEntry
    MAX-ACCESS  not-accessible
    STATUS      current
    DESCRIPTION "Resynchronization bandwidth."
    INDEX       { astaireBandwidthScope }
    ::= { astaireBandwidthTable 1 }

AstaireBandwidthTableEntry ::= SEQUENCE
{
    astaireBandwidthScope          INTEGER,
    astaireBandwidth               Unsigned32
}

astaireBandwidthScope OBJECT-TYPE
    SYNTAX      INTEGER {
                  scopePrevious5SecondPeriod(1)
                }
    MAX-ACCESS  not-accessible
    STATUS      current
    DESCRIPTION "The period over which the statistics were collected."
    ::= { astaireBandwidthTableEntry 1 }

astaireBandwidth OBJECT-TYPE
    SYNTAX      Unsigned32
    MAX-ACCESS  read-only
    STATUS      current
    DESCRIPTION "Resynchronization bandwidth (bytes per second) over the period."
    ::= { astaireBandwidthTableEntry 2 }

astaireConnectionTable OBJECT-TYPE
    SYNTAX SEQUENCE OF AstaireConnectionTableEntry
    MAX-ACCESS  not-accessible
    STATUS      current
    DESCRIPTION "Resynchronization statistics on a per-connection basis."
    ::= { astaire 6 }

astaireConnectionTableEntry OBJECT-TYPE
    SYNTAX      AstaireConnectionTableEntry
    MAX-ACCESS  not-accessible
    STATUS      current
    DESCRIPTION "Resynchronization statistics for a specific connection.  Entries only
                 exist while the connection is established - once it terminates, the entry
                 is deleted."
    INDEX { astaireConnectionInetAddrType,
            astaireConnectionInetAddr,
            astaireConnectionInetPort      }
    ::= { astaireConnectionTable 1 }

AstaireConnectionTableEntry ::= SEQUENCE
{
  astaireConnectionInetAddrType           InetAddressType,
  astaireConnectionInetAddr               InetAddress,
  astaireConnectionInetPort               Unsigned32,
  astaireConnectionBucketsNeedingResync   Unsigned32,
  astaireConnectionBucketsResynchronized  Unsigned32
}

astaireConnectionInetAddrType OBJECT-TYPE
    SYNTAX      InetAddressType
    MAX-ACCESS  not-accessible
    STATUS      current
    DESCRIPTION "Inet address type of the connection peer"
    ::= { astaireConnectionTableEntry 1 }

astaireConnectionInetAddr OBJECT-TYPE
    SYNTAX      InetAddress (SIZE (1..16))
    MAX-ACCESS  not-accessible
    STATUS      current
    DESCRIPTION "Inet address of the connection peer"
    ::= { astaireConnectionTableEntry 2 }

astaireConnectionInetPort OBJECT-TYPE
    SYNTAX      Unsigned32
    MAX-ACCESS  not-accessible
    STATUS      current
    DESCRIPTION "Port of the connection peer"
    ::= { astaireConnectionTableEntry 3 }

astaireConnectionBucketsNeedingResync OBJECT-TYPE
    SYNTAX      Unsigned32
    MAX-ACCESS  read-only
    STATUS      current
    DESCRIPTION "Count of buckets needing to be synchronized over this
                 connection for the current resynchronization operation."
    ::= { astaireConnectionTableEntry 4 }

astaireConnectionBucketsResynchronized OBJECT-TYPE
    SYNTAX      Unsigned32
    MAX-ACCESS  read-only
    STATUS      current
    DESCRIPTION "Number of buckets already resynchronized over this connection
                 during the current resynchronization operation."
    ::= { astaireConnectionTableEntry 5 }

astaireConnectionBucketTable OBJECT-TYPE
    SYNTAX SEQUENCE OF AstaireConnectionBucketTableEntry
    MAX-ACCESS  not-accessible
    STATUS      current
    DESCRIPTION "Resynchronization statistics on a per-connection and
                 per-bucket basis."
    ::= { astaire 7 }

astaireConnectionBucketTableEntry OBJECT-TYPE
    SYNTAX      AstaireConnectionBucketTableEntry
    MAX-ACCESS  not-accessible
    STATUS      current
    DESCRIPTION "Resynchronization statistics for a specific connection and
                 bucket."
    INDEX { astaireConnectionBucketInetAddrType,
            astaireConnectionBucketInetAddr,
            astaireConnectionBucketInetPort,
            astaireConnectionBucketId }
    ::= { astaireConnectionBucketTable 1 }

AstaireConnectionBucketTableEntry ::= SEQUENCE
{
  astaireConnectionBucketInetAddrType           InetAddressType,
  astaireConnectionBucketInetAddr               InetAddress (SIZE (1..16)),
  astaireConnectionBucketInetPort               Unsigned32,
  astaireConnectionBucketId                     Unsigned32,
  astaireConnectionBucketEntriesResynchronized  Unsigned32,
  astaireConnectionBucketDataResynchronized     Unsigned32,
  astaireConnectionBucketBandwidthTable         SEQUENCE OF AstaireConnectionBucketBandwidthTableEntry
}

astaireConnectionBucketInetAddrType OBJECT-TYPE
    SYNTAX      InetAddressType
    MAX-ACCESS  not-accessible
    STATUS      current
    DESCRIPTION "Inet address type of the connection peer"
    ::= { astaireConnectionBucketTableEntry 1 }

astaireConnectionBucketInetAddr OBJECT-TYPE
    SYNTAX      InetAddress (SIZE (1..16))
    MAX-ACCESS  not-accessible
    STATUS      current
    DESCRIPTION "Inet address of the connection peer"
    ::= { astaireConnectionBucketTableEntry 2 }

astaireConnectionBucketInetPort OBJECT-TYPE
    SYNTAX      Unsigned32
    MAX-ACCESS  not-accessible
    STATUS      current
    DESCRIPTION "Port of the connection peer"
    ::= { astaireConnectionBucketTableEntry 3 }

astaireConnectionBucketId OBJECT-TYPE
    SYNTAX      Unsigned32
    MAX-ACCESS  not-accessible
    STATUS      current
    DESCRIPTION "Identifier of this bucket."
    ::= { astaireConnectionBucketTableEntry 4 }

astaireConnectionBucketEntriesResynchronized OBJECT-TYPE
    SYNTAX      Unsigned32
    MAX-ACCESS  read-only
    STATUS      current
    DESCRIPTION "Number of entries already resynchronized during the current
                 resynchronization operation on this connection and bucket."
    ::= { astaireConnectionBucketTableEntry 5 }

astaireConnectionBucketDataResynchronized OBJECT-TYPE
    SYNTAX      Unsigned32
    MAX-ACCESS  read-only
    STATUS      current
    DESCRIPTION "Amout of data (in bytes) already resynchronized during the current
                 resynchronization operation on this connection and bucket."
    ::= { astaireConnectionBucketTableEntry 6 }

astaireConnectionBucketBandwidthTable OBJECT-TYPE
    SYNTAX SEQUENCE OF AstaireConnectionBucketBandwidthTableEntry
    MAX-ACCESS  not-accessible
    STATUS      current
    DESCRIPTION "Resynchronization bandwidth for this bucket for the given period."
    ::= { astaire 8 }

astaireConnectionBucketBandwidthTableEntry OBJECT-TYPE
    SYNTAX      AstaireConnectionBucketBandwidthTableEntry
    MAX-ACCESS  not-accessible
    STATUS      current
    DESCRIPTION "Resynchronization bandwidth for this bucket."
    INDEX       { astaireConnectionBucketBandwidthInetAddrType,
                  astaireConnectionBucketBandwidthInetAddr,
                  astaireConnectionBucketBandwidthInetPort,
                  astaireConnectionBucketBandwidthBucketId,
                  astaireConnectionBucketBandwidthScope }
    ::= { astaireConnectionBucketBandwidthTable 1 }

AstaireConnectionBucketBandwidthTableEntry ::= SEQUENCE
{
    astaireConnectionBucketBandwidthInetAddrType InetAddressType,
    astaireConnectionBucketBandwidthInetAddr     InetAddress (SIZE (1..16)),
    astaireConnectionBucketBandwidthInetPort     Unsigned32,
    astaireConnectionBucketBandwidthBucketId     Unsigned32,
    astaireConnectionBucketBandwidthScope        INTEGER,
    astaireConnectionBucketBandwidth             Unsigned32
}

astaireConnectionBucketBandwidthInetAddrType OBJECT-TYPE
    SYNTAX      InetAddressType
    MAX-ACCESS  not-accessible
    STATUS      current
    DESCRIPTION "Inet address type of the connection peer"
    ::= { astaireConnectionBucketBandwidthTableEntry 1 }

astaireConnectionBucketBandwidthInetAddr OBJECT-TYPE
    SYNTAX      InetAddress (SIZE (1..16))
    MAX-ACCESS  not-accessible
    STATUS      current
    DESCRIPTION "Inet address of the connection peer"
    ::= { astaireConnectionBucketBandwidthTableEntry 2 }

astaireConnectionBucketBandwidthInetPort OBJECT-TYPE
    SYNTAX      Unsigned32
    MAX-ACCESS  not-accessible
    STATUS      current
    DESCRIPTION "Port of the connection peer"
    ::= { astaireConnectionBucketBandwidthTableEntry 3 }

astaireConnectionBucketBandwidthBucketId OBJECT-TYPE
    SYNTAX      Unsigned32
    MAX-ACCESS  not-accessible
    STATUS      current
    DESCRIPTION "Identifier of this bucket."
    ::= { astaireConnectionBucketBandwidthTableEntry 4 }

astaireConnectionBucketBandwidthScope OBJECT-TYPE
    SYNTAX      INTEGER {
                  scopePrevious5SecondPeriod(1)
                }
    MAX-ACCESS  not-accessible
    STATUS      current
    DESCRIPTION "The period over which the statistics were collected."
    ::= { astaireConnectionBucketBandwidthTableEntry 5 }

astaireConnectionBucketBandwidth OBJECT-TYPE
    SYNTAX      Unsigned32
    MAX-ACCESS  read-only
    STATUS      current
    DESCRIPTION "Resynchronization bandwidth (bytes per second) over the period."
    ::= { astaireConnectionBucketBandwidthTableEntry 6 }

astaireGroup OBJECT-GROUP
    OBJECTS {
        astaireBucketsNeedingResync,
        astaireBucketsResynchronized,
        astaireEntriesResynchronized,
        astaireDataResynchronized,
        astaireBandwidthScope,
        astaireBandwidth,
        astaireConnectionInetAddrType,
        astaireConnectionInetAddr,
        astaireConnectionInetPort,
        astaireConnectionBucketsNeedingResync,
        astaireConnectionBucketsResynchronized,
        astaireConnectionBucketId,
        astaireConnectionBucketEntriesResynchronized,
        astaireConnectionBucketDataResynchronized,
        astaireConnectionBucketBandwidthScope,
        astaireConnectionBucketBandwidth
    }
    STATUS      current
    DESCRIPTION "Statistics exposed by Astaire"
    ::= { projectClearwaterObjectGroups 6 }

-- Chronos Entries

chronosRemainingNodesQuery OBJECT-TYPE
    SYNTAX      Unsigned32
    MAX-ACCESS  read-only
    STATUS      current
    DESCRIPTION "Current count of the remaining Chronos nodes to query during a
                 scaling operation."
    ::= { chronos 1 }

chronosTimersProcessedTable OBJECT-TYPE
    SYNTAX SEQUENCE OF ChronosTimersProcessedEntry
    MAX-ACCESS not-accessible
    STATUS current
    DESCRIPTION "Total number of timers processed handled by this Chronos over
                 the given period."
    ::= { chronos 2 }

chronosTimersProcessedEntry OBJECT-TYPE
    SYNTAX      ChronosTimersProcessedEntry
    MAX-ACCESS  not-accessible
    STATUS      current
    DESCRIPTION "The total number of timers processed"
    INDEX       { chronosTimersProcessedScope }
    ::= { chronosTimersProcessedTable 1 }

ChronosTimersProcessedEntry ::= SEQUENCE
{
  chronosTimersProcessedScope          INTEGER,
  chronosTimersProcessedCount          Unsigned32
}

chronosTimersProcessedScope OBJECT-TYPE
    SYNTAX      INTEGER {
                  scopePrevious5SecondPeriod(1)
                }
    MAX-ACCESS  not-accessible
    STATUS      current
    DESCRIPTION "The period over which the statistics were collected."
    ::= { chronosTimersProcessedEntry 1 }

chronosTimersProcessedCount OBJECT-TYPE
    SYNTAX      Unsigned32
    MAX-ACCESS  read-only
    STATUS      current
    DESCRIPTION "The total number of timers processed over the period."
    ::= { chronosTimersProcessedEntry 2 }

chronosInvalidTimersProcessedTable OBJECT-TYPE
    SYNTAX SEQUENCE OF ChronosInvalidTimersProcessedEntry
    MAX-ACCESS not-accessible
    STATUS current
    DESCRIPTION "Total number of invalid timers processed by this Chronos over
                 the given period."
    ::= { chronos 3 }

chronosInvalidTimersProcessedEntry OBJECT-TYPE
    SYNTAX      ChronosInvalidTimersProcessedEntry
    MAX-ACCESS  not-accessible
    STATUS      current
    DESCRIPTION "The total number of invalid timers processed"
    INDEX       { chronosInvalidTimersProcessedScope }
    ::= { chronosInvalidTimersProcessedTable 1 }

ChronosInvalidTimersProcessedEntry ::= SEQUENCE
{
  chronosInvalidTimersProcessedScope          INTEGER,
  chronosInvalidTimersProcessedCount          Unsigned32
}

chronosInvalidTimersProcessedScope OBJECT-TYPE
    SYNTAX      INTEGER {
                  scopePrevious5SecondPeriod(1)
                }
    MAX-ACCESS  not-accessible
    STATUS      current
    DESCRIPTION "The period over which the statistics were collected."
    ::= { chronosInvalidTimersProcessedEntry 1 }

chronosInvalidTimersProcessedCount OBJECT-TYPE
    SYNTAX      Unsigned32
    MAX-ACCESS  read-only
    STATUS      current
    DESCRIPTION "The total number of invalid timers processed over the period."
    ::= { chronosInvalidTimersProcessedEntry 2 }

chronosTotalTimersTable OBJECT-TYPE
    SYNTAX SEQUENCE OF ChronosTotalTimersEntry
    MAX-ACCESS         not-accessible
    STATUS             current
    DESCRIPTION        "The total number of timers this Chronos node
                       is managing. This includes timers for which this node
                       is primary, and timers for which this node is a backup"
    ::= { chronos 4 }

chronosTotalTimersEntry OBJECT-TYPE
    SYNTAX      ChronosTotalTimersEntry
    MAX-ACCESS  not-accessible
    STATUS      current
    DESCRIPTION "The average, variance, HWM and LWM of
                 the total timers stored by this Chronos"
    INDEX       { chronosTotalTimersScope }
    ::= { chronosTotalTimersTable 1 }

ChronosTotalTimersEntry ::= SEQUENCE
{
  chronosTotalTimersScope        INTEGER
  chronosTotalTimersAverage      Unsigned32,
  chronosTotalTimersVariance     Unsigned32,
  chronosTotalTimersHWM          Unsigned32,
  chronosTotalTimersLWM          Unsigned32,
}

chronosTotalTimersScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { chronosTotalTimersEntry 1 }

chronosTotalTimersAverage OBJECT-TYPE
    SYNTAX      Unsigned32
    MAX-ACCESS  read-only
    STATUS      current
    DESCRIPTION "The average of the total number of timers
                 stored over the period."
    ::= { chronosTotalTimersEntry 2 }

chronosTotalTimersVariance OBJECT-TYPE
    SYNTAX      Unsigned32
    MAX-ACCESS  read-only
    STATUS      current
    DESCRIPTION "The variance of the total number of timers
                 stored over the period."
    ::= { chronosTotalTimersEntry 3 }

chronosTotalTimersHWM OBJECT-TYPE
    SYNTAX      Unsigned32
    MAX-ACCESS  read-only
    STATUS      current
    DESCRIPTION "The highest number of total timers stored
                 over the period."
    ::= { chronosTotalTimersEntry 4 }

chronosTotalTimersLWM OBJECT-TYPE
    SYNTAX      Unsigned32
    MAX-ACCESS  read-only
    STATUS      current
    DESCRIPTION "The lowest number of total timers stored
                 over the period."
    ::= { chronosTotalTimersEntry 5 }

chronosCurrentTimers OBJECT-TYPE
    SYNTAX      Unsigned32
    MAX-ACCESS  read-only
    STATUS      current
    DESCRIPTION "The current number of timers that Chronos
                 is managing. This includes timers for which this node
                 is primary, and timers for which this node is a backup"
    ::= { chronos 5 }

chronosGroup OBJECT-GROUP
    OBJECTS {
        chronosRemainingNodesQuery,
        chronosTimersProcessedCount,
        chronosInvalidTimersProcessedCount,
        chronosTotalTimersAverage,
        chronosTotalTimersVariance,
        chronosTotalTimersHWM,
        chronosTotalTimersLWM,
        chronosCurrentTimers
    }
    STATUS      current
    DESCRIPTION "Statistics exposed by Chronos"
    ::= { projectClearwaterObjectGroups 7 }

-- Gemini Entries

geminiIncomingSIPTransactionsTable OBJECT-TYPE
    SYNTAX SEQUENCE OF GeminiIncomingSIPTransactionsEntry
    MAX-ACCESS not-accessible
    STATUS current
    DESCRIPTION "Counts the number of attempts, successes and failures
                 of incoming SIP transactions for Gemini"
    ::= { gemini 1 }

geminiIncomingSIPTransactionsEntry OBJECT-TYPE
    SYNTAX      GeminiIncomingSIPTransactionsEntry
    MAX-ACCESS  not-accessible
    STATUS      current
    DESCRIPTION "The number of attempts, successes and failures for
                 incoming SIP transactions for Gemini"
    INDEX       { geminiIncomingSIPTransactionsTimeScope,
                  geminiIncomingSIPTransactionsRequestScope }
    ::= { geminiIncomingSIPTransactionsTable 1 }

GeminiIncomingSIPTransactionsEntry ::= SEQUENCE
{
  geminiIncomingSIPTransactionsTimeScope      INTEGER,
  geminiIncomingSIPTransactionsRequestScope   INTEGER,
  geminiIncomingSIPTransactionsAttempts       Unsigned32,
  geminiIncomingSIPTransactionsSuccesses      Unsigned32,
  geminiIncomingSIPTransactionsFailures       Unsigned32
}

geminiIncomingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { geminiIncomingSIPTransactionsEntry 1 }

geminiIncomingSIPTransactionsRequestScope OBJECT-TYPE
    SYNTAX      RequestType
    MAX-ACCESS  not-accessible
    STATUS      current
    DESCRIPTION "The method type of the incoming transaction."
    ::= { geminiIncomingSIPTransactionsEntry 2 }

geminiIncomingSIPTransactionsAttempts OBJECT-TYPE
    SYNTAX      Unsigned32
    MAX-ACCESS  read-only
    STATUS      current
    DESCRIPTION "The number of incoming SIP transactions over the time period."
    ::= { geminiIncomingSIPTransactionsEntry 3 }

geminiIncomingSIPTransactionsSuccesses OBJECT-TYPE
    SYNTAX      Unsigned32
    MAX-ACCESS  read-only
    STATUS      current
    DESCRIPTION "The number of successful incoming SIP transactions over the
                 time period."
    ::= { geminiIncomingSIPTransactionsEntry 4 }

geminiIncomingSIPTransactionsFailures OBJECT-TYPE
    SYNTAX      Unsigned32
    MAX-ACCESS  read-only
    STATUS      current
    DESCRIPTION "The number of failed incoming SIP transactions over the
                 time period."
    ::= { geminiIncomingSIPTransactionsEntry 5 }

geminiOutgoingSIPTransactionsTable OBJECT-TYPE
    SYNTAX SEQUENCE OF GeminiOutgoingSIPTransactionsEntry
    MAX-ACCESS not-accessible
    STATUS current
    DESCRIPTION "Counts the number of attempts, successes and failures
                 of outgoing SIP transactions for Gemini."
    ::= { gemini 2 }

geminiOutgoingSIPTransactionsEntry OBJECT-TYPE
    SYNTAX      GeminiOutgoingSIPTransactionsEntry
    MAX-ACCESS  not-accessible
    STATUS      current
    DESCRIPTION "The number of attempts, successes and failures for
                 outgoing SIP transactions for Gemini."
    INDEX       { geminiOutgoingSIPTransactionsTimeScope,
                  geminiOutgoingSIPTransactionsRequestScope }
    ::= { geminiOutgoingSIPTransactionsTable 1 }

GeminiOutgoingSIPTransactionsEntry ::= SEQUENCE
{
  geminiOutgoingSIPTransactionsTimeScope      INTEGER,
  geminiOutgoingSIPTransactionsRequestScope   INTEGER,
  geminiOutgoingSIPTransactionsAttempts       Unsigned32,
  geminiOutgoingSIPTransactionsSuccesses      Unsigned32,
  geminiOutgoingSIPTransactionsFailures       Unsigned32
}

geminiOutgoingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { geminiOutgoingSIPTransactionsEntry 1 }

geminiOutgoingSIPTransactionsRequestScope OBJECT-TYPE
    SYNTAX      RequestType
    MAX-ACCESS  not-accessible
    STATUS      current
    DESCRIPTION "The method type of the outgoing transaction."
    ::= { geminiOutgoingSIPTransactionsEntry 2 }

geminiOutgoingSIPTransactionsAttempts OBJECT-TYPE
    SYNTAX      Unsigned32
    MAX-ACCESS  read-only
    STATUS      current
    DESCRIPTION "The number of outgoing SIP transactions over the time period."
    ::= { geminiOutgoingSIPTransactionsEntry 3 }

geminiOutgoingSIPTransactionsSuccesses OBJECT-TYPE
    SYNTAX      Unsigned32
    MAX-ACCESS  read-only
    STATUS      current
    DESCRIPTION "The number of successful outgoing SIP transactions over the
                 time period."
    ::= { geminiOutgoingSIPTransactionsEntry 4 }

geminiOutgoingSIPTransactionsFailures OBJECT-TYPE
    SYNTAX      Unsigned32
    MAX-ACCESS  read-only
    STATUS      current
    DESCRIPTION "The number of failed outgoing SIP transactions over the
                 time period."
    ::= { geminiOutgoingSIPTransactionsEntry 5 }

geminiGroup OBJECT-GROUP
    OBJECTS {
      geminiIncomingSIPTransactionsAttempts,
      geminiIncomingSIPTransactionsSuccesses,
      geminiIncomingSIPTransactionsFailures,
      geminiOutgoingSIPTransactionsAttempts,
      geminiOutgoingSIPTransactionsSuccesses,
      geminiOutgoingSIPTransactionsFailures
    }
    STATUS    current
    DESCRIPTION "Statistics exposed by Gemini"
    ::= { projectClearwaterObjectGroups 11  }

END
